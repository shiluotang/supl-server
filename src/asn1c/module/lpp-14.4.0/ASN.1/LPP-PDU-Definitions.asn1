LPP-PDU-Definitions {
itu-t (0) identified-organization (4) etsi (0) mobileDomain (0)
eps-Access (21) modules (3) lpp (7) version1 (1) lpp-PDU-Definitions (1) }

DEFINITIONS AUTOMATIC TAGS ::=

BEGIN

-- ASN1STOP
-- ASN1START

LPP-Message ::= SEQUENCE {
    transactionID           LPP-TransactionID   OPTIONAL,   -- Need ON
    endTransaction          BOOLEAN,
    sequenceNumber          SequenceNumber      OPTIONAL,   -- Need ON
    acknowledgement         Acknowledgement     OPTIONAL,   -- Need ON
    lpp-MessageBody         LPP-MessageBody     OPTIONAL    -- Need ON
}

SequenceNumber ::= INTEGER (0..255)

Acknowledgement ::= SEQUENCE {
    ackRequested    BOOLEAN,
    ackIndicator    SequenceNumber      OPTIONAL
}

-- ASN1STOP
-- ASN1START

LPP-MessageBody ::= CHOICE {
    c1                      CHOICE {
        requestCapabilities         RequestCapabilities,
        provideCapabilities         ProvideCapabilities,
        requestAssistanceData       RequestAssistanceData,
        provideAssistanceData       ProvideAssistanceData,
        requestLocationInformation  RequestLocationInformation,
        provideLocationInformation  ProvideLocationInformation,
        abort                       Abort,
        error                       Error,
        spare7 NULL, spare6 NULL, spare5 NULL, spare4 NULL,
        spare3 NULL, spare2 NULL, spare1 NULL, spare0 NULL
    },
    messageClassExtension   SEQUENCE {}
}

-- ASN1STOP
-- ASN1START

LPP-TransactionID ::= SEQUENCE {
    initiator               Initiator,
    transactionNumber       TransactionNumber,
    ...
}

Initiator ::= ENUMERATED {
    locationServer,
    targetDevice,
    ...
}

TransactionNumber ::= INTEGER (0..255)

-- ASN1STOP
-- ASN1START

RequestCapabilities ::= SEQUENCE {
    criticalExtensions      CHOICE {
        c1                      CHOICE {
            requestCapabilities-r9      RequestCapabilities-r9-IEs,
            spare3 NULL, spare2 NULL, spare1 NULL
        },
        criticalExtensionsFuture    SEQUENCE {}
    }
}

RequestCapabilities-r9-IEs ::= SEQUENCE {
    commonIEsRequestCapabilities        CommonIEsRequestCapabilities        OPTIONAL,   -- Need ON
    a-gnss-RequestCapabilities          A-GNSS-RequestCapabilities          OPTIONAL,   -- Need ON
    otdoa-RequestCapabilities           OTDOA-RequestCapabilities           OPTIONAL,   -- Need ON
    ecid-RequestCapabilities            ECID-RequestCapabilities            OPTIONAL,   -- Need ON
    epdu-RequestCapabilities            EPDU-Sequence                       OPTIONAL,   -- Need ON
    ...,
      sensor-RequestCapabilities-r13  Sensor-RequestCapabilities-r13      OPTIONAL,   -- Need ON
        tbs-RequestCapabilities-r13     TBS-RequestCapabilities-r13         OPTIONAL,   -- Need ON
        wlan-RequestCapabilities-r13    WLAN-RequestCapabilities-r13        OPTIONAL,   -- Need ON
        bt-RequestCapabilities-r13      BT-RequestCapabilities-r13          OPTIONAL    -- Need ON

}

-- ASN1STOP
-- ASN1START

ProvideCapabilities ::= SEQUENCE {
    criticalExtensions      CHOICE {
        c1                      CHOICE {
            provideCapabilities-r9      ProvideCapabilities-r9-IEs,
            spare3 NULL, spare2 NULL, spare1 NULL
        },
        criticalExtensionsFuture    SEQUENCE {}
    }
}

ProvideCapabilities-r9-IEs ::= SEQUENCE {
    commonIEsProvideCapabilities        CommonIEsProvideCapabilities        OPTIONAL,
    a-gnss-ProvideCapabilities          A-GNSS-ProvideCapabilities          OPTIONAL,
    otdoa-ProvideCapabilities           OTDOA-ProvideCapabilities           OPTIONAL,
    ecid-ProvideCapabilities            ECID-ProvideCapabilities            OPTIONAL,
    epdu-ProvideCapabilities            EPDU-Sequence                       OPTIONAL,
    ...,
      sensor-ProvideCapabilities-r13  Sensor-ProvideCapabilities-r13      OPTIONAL,
        tbs-ProvideCapabilities-r13     TBS-ProvideCapabilities-r13         OPTIONAL,
        wlan-ProvideCapabilities-r13    WLAN-ProvideCapabilities-r13        OPTIONAL,
        bt-ProvideCapabilities-r13      BT-ProvideCapabilities-r13          OPTIONAL

}

-- ASN1STOP
-- ASN1START

RequestAssistanceData ::= SEQUENCE {
    criticalExtensions      CHOICE {
        c1                      CHOICE {
            requestAssistanceData-r9    RequestAssistanceData-r9-IEs,
            spare3 NULL, spare2 NULL, spare1 NULL
        },
        criticalExtensionsFuture    SEQUENCE {}
    }
}

RequestAssistanceData-r9-IEs ::= SEQUENCE {
    commonIEsRequestAssistanceData      CommonIEsRequestAssistanceData      OPTIONAL,
    a-gnss-RequestAssistanceData        A-GNSS-RequestAssistanceData        OPTIONAL,
    otdoa-RequestAssistanceData         OTDOA-RequestAssistanceData         OPTIONAL,
    epdu-RequestAssistanceData          EPDU-Sequence                       OPTIONAL,
    ...,
      sensor-RequestAssistanceData-r14
                                        Sensor-RequestAssistanceData-r14    OPTIONAL,
        tbs-RequestAssistanceData-r14   TBS-RequestAssistanceData-r14       OPTIONAL,
        wlan-RequestAssistanceData-r14  WLAN-RequestAssistanceData-r14      OPTIONAL

}

-- ASN1STOP
-- ASN1START

ProvideAssistanceData ::= SEQUENCE {
    criticalExtensions      CHOICE {
        c1                      CHOICE {
            provideAssistanceData-r9    ProvideAssistanceData-r9-IEs,
            spare3 NULL, spare2 NULL, spare1 NULL
        },
        criticalExtensionsFuture    SEQUENCE {}
    }
}

ProvideAssistanceData-r9-IEs ::= SEQUENCE {
    commonIEsProvideAssistanceData      CommonIEsProvideAssistanceData      OPTIONAL,   -- Need ON
    a-gnss-ProvideAssistanceData        A-GNSS-ProvideAssistanceData        OPTIONAL,   -- Need ON
    otdoa-ProvideAssistanceData         OTDOA-ProvideAssistanceData         OPTIONAL,   -- Need ON
    epdu-Provide-Assistance-Data        EPDU-Sequence                       OPTIONAL,   -- Need ON
    ...,

    sensor-ProvideAssistanceData-r14    Sensor-ProvideAssistanceData-r14    OPTIONAL,   -- Need ON
    tbs-ProvideAssistanceData-r14       TBS-ProvideAssistanceData-r14       OPTIONAL,   -- Need ON
    wlan-ProvideAssistanceData-r14      WLAN-ProvideAssistanceData-r14      OPTIONAL    -- Need ON

}

-- ASN1STOP
-- ASN1START

RequestLocationInformation ::= SEQUENCE {
    criticalExtensions      CHOICE {
        c1                      CHOICE {
            requestLocationInformation-r9   RequestLocationInformation-r9-IEs,
            spare3 NULL, spare2 NULL, spare1 NULL
        },
        criticalExtensionsFuture    SEQUENCE {}
    }
}

RequestLocationInformation-r9-IEs ::= SEQUENCE {
    commonIEsRequestLocationInformation
                                        CommonIEsRequestLocationInformation OPTIONAL,   -- Need ON
    a-gnss-RequestLocationInformation   A-GNSS-RequestLocationInformation   OPTIONAL,   -- Need ON
    otdoa-RequestLocationInformation    OTDOA-RequestLocationInformation    OPTIONAL,   -- Need ON
    ecid-RequestLocationInformation     ECID-RequestLocationInformation     OPTIONAL,   -- Need ON
    epdu-RequestLocationInformation     EPDU-Sequence                       OPTIONAL,   -- Need ON
    ...,

    sensor-RequestLocationInformation-r13
                                        Sensor-RequestLocationInformation-r13
                                                                            OPTIONAL,   -- Need ON
    tbs-RequestLocationInformation-r13  TBS-RequestLocationInformation-r13  OPTIONAL,   -- Need ON
    wlan-RequestLocationInformation-r13 WLAN-RequestLocationInformation-r13 OPTIONAL,   -- Need ON
    bt-RequestLocationInformation-r13   BT-RequestLocationInformation-r13   OPTIONAL    -- Need ON

}

-- ASN1STOP
-- ASN1START

ProvideLocationInformation ::= SEQUENCE {
    criticalExtensions      CHOICE {
        c1                      CHOICE {
            provideLocationInformation-r9   ProvideLocationInformation-r9-IEs,
            spare3 NULL, spare2 NULL, spare1 NULL
        },
        criticalExtensionsFuture    SEQUENCE {}
    }
}

ProvideLocationInformation-r9-IEs ::= SEQUENCE {
    commonIEsProvideLocationInformation
                                        CommonIEsProvideLocationInformation OPTIONAL,
    a-gnss-ProvideLocationInformation   A-GNSS-ProvideLocationInformation   OPTIONAL,
    otdoa-ProvideLocationInformation    OTDOA-ProvideLocationInformation    OPTIONAL,
    ecid-ProvideLocationInformation     ECID-ProvideLocationInformation     OPTIONAL,
    epdu-ProvideLocationInformation     EPDU-Sequence                       OPTIONAL,
    ...,

    sensor-ProvideLocationInformation-r13
                                        Sensor-ProvideLocationInformation-r13
                                                                            OPTIONAL,
    tbs-ProvideLocationInformation-r13  TBS-ProvideLocationInformation-r13  OPTIONAL,
    wlan-ProvideLocationInformation-r13 WLAN-ProvideLocationInformation-r13 OPTIONAL,
    bt-ProvideLocationInformation-r13   BT-ProvideLocationInformation-r13   OPTIONAL

}

-- ASN1STOP
-- ASN1START

Abort ::= SEQUENCE {
    criticalExtensions      CHOICE {
        c1                      CHOICE {
            abort-r9        Abort-r9-IEs,
            spare3 NULL, spare2 NULL, spare1 NULL
        },
        criticalExtensionsFuture    SEQUENCE {}
    }
}

Abort-r9-IEs ::= SEQUENCE {
    commonIEsAbort      CommonIEsAbort          OPTIONAL,   -- Need ON
    ...,
    epdu-Abort          EPDU-Sequence           OPTIONAL    -- Need ON
}

-- ASN1STOP
-- ASN1START

Error ::= CHOICE {
    error-r9                    Error-r9-IEs,
    criticalExtensionsFuture    SEQUENCE {}
}

Error-r9-IEs ::= SEQUENCE {
    commonIEsError      CommonIEsError          OPTIONAL,   -- Need ON
    ...,
    epdu-Error          EPDU-Sequence           OPTIONAL    -- Need ON
}

-- ASN1STOP
-- ASN1START

AccessTypes ::= SEQUENCE {
    accessTypes     BIT STRING {    eutra       (0),
                                    utra        (1),
                                    gsm         (2),
                                    nb-iot      (3) } (SIZE (1..8)),
    ...
}

-- ASN1STOP
-- ASN1START

ARFCN-ValueEUTRA ::= INTEGER (0..maxEARFCN)

ARFCN-ValueEUTRA-v9a0 ::=   INTEGER (maxEARFCN-Plus1..maxEARFCN2)

ARFCN-ValueEUTRA-r14  ::=   INTEGER (0..maxEARFCN2)

maxEARFCN                   INTEGER ::= 65535   -- Maximum value of EUTRA carrier frequency

maxEARFCN-Plus1             INTEGER ::= 65536   -- Lowest value extended EARFCN range

maxEARFCN2                  INTEGER ::= 262143  -- Highest value extended EARFCN range

-- ASN1STOP
-- ASN1START

ARFCN-ValueUTRA ::= INTEGER (0..16383)

-- ASN1STOP
-- ASN1START

CarrierFreq-NB-r14 ::=      SEQUENCE {
    carrierFreq-r14             ARFCN-ValueEUTRA-r14,
    carrierFreqOffset-r14       CarrierFreqOffsetNB-r14             OPTIONAL,
    ...
}

-- ASN1STOP
-- ASN1START

CarrierFreqOffsetNB-r14 ::=     ENUMERATED {
                                    v-10, v-9, v-8, v-7, v-6, v-5, v-4, v-3, v-2, v-1, v-0dot5,
                                      v0,  v1,  v2,  v3,  v4,  v5,  v6,  v7,  v8,  v9
                                    }

-- ASN1STOP
-- ASN1START

CellGlobalIdEUTRA-AndUTRA ::= SEQUENCE {
    plmn-Identity       SEQUENCE {
                            mcc     SEQUENCE (SIZE (3))     OF INTEGER (0..9),
                            mnc     SEQUENCE (SIZE (2..3))  OF INTEGER (0..9)
                        },
    cellIdentity        CHOICE {
        eutra   BIT STRING (SIZE (28)),
        utra    BIT STRING (SIZE (32))
    },
    ...
}

-- ASN1STOP
-- ASN1START

CellGlobalIdGERAN ::= SEQUENCE {
    plmn-Identity       SEQUENCE {
                            mcc     SEQUENCE (SIZE (3))     OF INTEGER (0..9),
                            mnc     SEQUENCE (SIZE (2..3))  OF INTEGER (0..9)
                            },
    locationAreaCode        BIT STRING (SIZE (16)),
    cellIdentity            BIT STRING (SIZE (16)),
    ...
}

-- ASN1STOP
-- ASN1START

ECGI ::= SEQUENCE {
    mcc             SEQUENCE (SIZE (3))     OF INTEGER (0..9),
    mnc             SEQUENCE (SIZE (2..3))  OF INTEGER (0..9),
    cellidentity    BIT STRING (SIZE (28))
}

-- ASN1STOP
-- ASN1START

Ellipsoid-Point ::= SEQUENCE {
    latitudeSign                ENUMERATED {north, south},
    degreesLatitude             INTEGER (0..8388607),           -- 23 bit field
    degreesLongitude            INTEGER (-8388608..8388607)     -- 24 bit field
}

-- ASN1STOP
-- ASN1START

Ellipsoid-PointWithUncertaintyCircle ::= SEQUENCE {
    latitudeSign                ENUMERATED {north, south},
    degreesLatitude             INTEGER (0..8388607),           -- 23 bit field
    degreesLongitude            INTEGER (-8388608..8388607),    -- 24 bit field
    uncertainty                 INTEGER (0..127)
}

-- ASN1STOP
-- ASN1START

EllipsoidPointWithUncertaintyEllipse ::= SEQUENCE {
    latitudeSign                ENUMERATED {north, south},
    degreesLatitude             INTEGER (0..8388607),           -- 23 bit field
    degreesLongitude            INTEGER (-8388608..8388607),    -- 24 bit field
    uncertaintySemiMajor        INTEGER (0..127),
    uncertaintySemiMinor        INTEGER (0..127),
    orientationMajorAxis        INTEGER (0..179),
    confidence                  INTEGER (0..100)
}

-- ASN1STOP
-- ASN1START

EllipsoidPointWithAltitude ::= SEQUENCE {
    latitudeSign                ENUMERATED {north, south},
    degreesLatitude             INTEGER (0..8388607),           -- 23 bit field
    degreesLongitude            INTEGER (-8388608..8388607),    -- 24 bit field
    altitudeDirection           ENUMERATED {height, depth},
    altitude                    INTEGER (0..32767)              -- 15 bit field
}

-- ASN1STOP
-- ASN1START

EllipsoidPointWithAltitudeAndUncertaintyEllipsoid ::= SEQUENCE {
    latitudeSign                ENUMERATED {north, south},
    degreesLatitude             INTEGER (0..8388607),           -- 23 bit field
    degreesLongitude            INTEGER (-8388608..8388607),    -- 24 bit field
    altitudeDirection           ENUMERATED {height, depth},
    altitude                    INTEGER (0..32767),             -- 15 bit field
    uncertaintySemiMajor        INTEGER (0..127),
    uncertaintySemiMinor        INTEGER (0..127),
    orientationMajorAxis        INTEGER (0..179),
    uncertaintyAltitude         INTEGER (0..127),
    confidence                  INTEGER (0..100)
}

-- ASN1STOP
-- ASN1START

EllipsoidArc ::= SEQUENCE {
    latitudeSign                ENUMERATED {north, south},
    degreesLatitude             INTEGER (0..8388607),           -- 23 bit field
    degreesLongitude            INTEGER (-8388608..8388607),    -- 24 bit field
    innerRadius                 INTEGER (0..65535),             -- 16 bit field,
    uncertaintyRadius           INTEGER (0..127),
    offsetAngle                 INTEGER (0..179),
    includedAngle               INTEGER (0..179),
    confidence                  INTEGER (0..100)
}

-- ASN1STOP
-- ASN1START

EPDU-Sequence ::= SEQUENCE (SIZE (1..maxEPDU)) OF EPDU

maxEPDU INTEGER ::= 16

EPDU ::= SEQUENCE {
    ePDU-Identifier         EPDU-Identifier,
    ePDU-Body               EPDU-Body
}

EPDU-Identifier ::= SEQUENCE {
    ePDU-ID                 EPDU-ID,
    ePDU-Name               EPDU-Name       OPTIONAL,
    ...
}

EPDU-ID ::= INTEGER (1..256)

EPDU-Name ::= VisibleString (SIZE (1..32))

EPDU-Body ::= OCTET STRING

-- ASN1STOP
-- ASN1START

HorizontalVelocity ::= SEQUENCE {
    bearing                     INTEGER(0..359),
    horizontalSpeed             INTEGER(0..2047)
}

-- ASN1STOP
-- ASN1START

HorizontalWithVerticalVelocity ::= SEQUENCE {
    bearing                     INTEGER(0..359),
    horizontalSpeed             INTEGER(0..2047),
    verticalDirection           ENUMERATED{upward, downward},
    verticalSpeed               INTEGER(0..255)
}

-- ASN1STOP
-- ASN1START

HorizontalVelocityWithUncertainty ::= SEQUENCE {
    bearing                     INTEGER(0..359),
    horizontalSpeed             INTEGER(0..2047),
    uncertaintySpeed            INTEGER(0..255)
}

-- ASN1STOP
-- ASN1START

HorizontalWithVerticalVelocityAndUncertainty ::= SEQUENCE {
    bearing                     INTEGER(0..359),
    horizontalSpeed             INTEGER(0..2047),
    verticalDirection           ENUMERATED{upward, downward},
    verticalSpeed               INTEGER(0..255),
    horizontalUncertaintySpeed  INTEGER(0..255),
    verticalUncertaintySpeed    INTEGER(0..255)
}

-- ASN1STOP
-- ASN1START

LocationCoordinateTypes ::= SEQUENCE {
    ellipsoidPoint                                          BOOLEAN,
    ellipsoidPointWithUncertaintyCircle                     BOOLEAN,
    ellipsoidPointWithUncertaintyEllipse                    BOOLEAN,
    polygon                                                 BOOLEAN,
    ellipsoidPointWithAltitude                              BOOLEAN,
    ellipsoidPointWithAltitudeAndUncertaintyEllipsoid       BOOLEAN,
    ellipsoidArc                                            BOOLEAN,
    ...
}

-- ASN1STOP
-- ASN1START

Polygon ::= SEQUENCE (SIZE (3..15)) OF PolygonPoints

PolygonPoints ::= SEQUENCE {
    latitudeSign                ENUMERATED {north, south},
    degreesLatitude             INTEGER (0..8388607),           -- 23 bit field
    degreesLongitude            INTEGER (-8388608..8388607)     -- 24 bit field
}

-- ASN1STOP
-- ASN1START

PositioningModes ::= SEQUENCE {
    posModes        BIT STRING {    standalone  (0),
                                    ue-based    (1),
                                    ue-assisted (2)  } (SIZE (1..8)),
    ...
}

-- ASN1STOP
-- ASN1START

VelocityTypes ::= SEQUENCE {
    horizontalVelocity                                      BOOLEAN,
    horizontalWithVerticalVelocity                          BOOLEAN,
    horizontalVelocityWithUncertainty                       BOOLEAN,
    horizontalWithVerticalVelocityAndUncertainty            BOOLEAN,
    ...
}

-- ASN1STOP
-- ASN1START

CommonIEsRequestCapabilities ::= SEQUENCE {
    ...
}

-- ASN1STOP
-- ASN1START

CommonIEsProvideCapabilities ::= SEQUENCE {
    ...
}

-- ASN1STOP
-- ASN1START

CommonIEsRequestAssistanceData ::= SEQUENCE {
    primaryCellID       ECGI        OPTIONAL,   -- Cond EUTRA
    ...
}

-- ASN1STOP
-- ASN1START

CommonIEsProvideAssistanceData ::= SEQUENCE {
    ...
}

-- ASN1STOP
-- ASN1START

CommonIEsRequestLocationInformation ::= SEQUENCE {
    locationInformationType     LocationInformationType,
    triggeredReporting          TriggeredReportingCriteria  OPTIONAL,   -- Cond ECID
    periodicalReporting         PeriodicalReportingCriteria OPTIONAL,   -- Need ON
    additionalInformation       AdditionalInformation       OPTIONAL,   -- Need ON
    qos                         QoS                         OPTIONAL,   -- Need ON
    environment                 Environment                 OPTIONAL,   -- Need ON
    locationCoordinateTypes     LocationCoordinateTypes     OPTIONAL,   -- Need ON
    velocityTypes               VelocityTypes               OPTIONAL,   -- Need ON
    ...,

        messageSizeLimitNB-r14  MessageSizeLimitNB-r14      OPTIONAL    -- Need ON

}

LocationInformationType ::= ENUMERATED {
    locationEstimateRequired,
    locationMeasurementsRequired,
    locationEstimatePreferred,
    locationMeasurementsPreferred,
    ...
}

PeriodicalReportingCriteria ::=     SEQUENCE {
    reportingAmount                     ENUMERATED {
                                            ra1, ra2, ra4, ra8, ra16, ra32,
                                            ra64, ra-Infinity
                                        } DEFAULT ra-Infinity,
    reportingInterval                   ENUMERATED {
                                            noPeriodicalReporting, ri0-25,
                                            ri0-5, ri1, ri2, ri4, ri8, ri16, ri32, ri64
                                        }
}

TriggeredReportingCriteria ::=      SEQUENCE {
    cellChange                          BOOLEAN,
    reportingDuration                   ReportingDuration,
    ...
}

ReportingDuration ::=               INTEGER (0..255)

AdditionalInformation ::= ENUMERATED {
    onlyReturnInformationRequested,
    mayReturnAditionalInformation,
    ...
}

QoS ::= SEQUENCE {
    horizontalAccuracy          HorizontalAccuracy      OPTIONAL,   -- Need ON
    verticalCoordinateRequest   BOOLEAN,
    verticalAccuracy            VerticalAccuracy        OPTIONAL,   -- Need ON
    responseTime                ResponseTime            OPTIONAL,   -- Need ON
    velocityRequest             BOOLEAN,
    ...,
      responseTimeNB-r14      ResponseTimeNB-r14      OPTIONAL    -- Need ON

}

HorizontalAccuracy ::= SEQUENCE {
    accuracy        INTEGER(0..127),
    confidence      INTEGER(0..100),
    ...
}

VerticalAccuracy ::= SEQUENCE {
    accuracy        INTEGER(0..127),
    confidence      INTEGER(0..100),
    ...
}

ResponseTime ::= SEQUENCE {
    time                                INTEGER (1..128),
    ...,
      responseTimeEarlyFix-r12        INTEGER (1..128)        OPTIONAL        -- Need ON

}

ResponseTimeNB-r14 ::= SEQUENCE {
    timeNB-r14                          INTEGER (1..512),
    responseTimeEarlyFixNB-r14          INTEGER (1..512)        OPTIONAL,       -- Need ON
    ...
}

Environment ::= ENUMERATED {
    badArea,
    notBadArea,
    mixedArea,
    ...
}

MessageSizeLimitNB-r14 ::= SEQUENCE {
    measurementLimit-r14                INTEGER (1..512)        OPTIONAL,       -- Need ON
    ...
}

-- ASN1STOP
-- ASN1START

CommonIEsProvideLocationInformation ::= SEQUENCE {
    locationEstimate            LocationCoordinates     OPTIONAL,
    velocityEstimate            Velocity                OPTIONAL,
    locationError               LocationError           OPTIONAL,
    ...,
      earlyFixReport-r12      EarlyFixReport-r12      OPTIONAL
    ,
      locationSource-r13      LocationSource-r13      OPTIONAL,
        locationTimestamp-r13   UTCTime                 OPTIONAL

}

LocationCoordinates ::= CHOICE {
    ellipsoidPoint                              Ellipsoid-Point,
    ellipsoidPointWithUncertaintyCircle         Ellipsoid-PointWithUncertaintyCircle,
    ellipsoidPointWithUncertaintyEllipse        EllipsoidPointWithUncertaintyEllipse,
    polygon                                     Polygon,
    ellipsoidPointWithAltitude                  EllipsoidPointWithAltitude,
    ellipsoidPointWithAltitudeAndUncertaintyEllipsoid
                                                EllipsoidPointWithAltitudeAndUncertaintyEllipsoid,
    ellipsoidArc                                EllipsoidArc,
    ...
}

Velocity ::= CHOICE {
    horizontalVelocity                          HorizontalVelocity,
    horizontalWithVerticalVelocity              HorizontalWithVerticalVelocity,
    horizontalVelocityWithUncertainty           HorizontalVelocityWithUncertainty,
    horizontalWithVerticalVelocityAndUncertainty
                                                HorizontalWithVerticalVelocityAndUncertainty,
    ...
}

LocationError ::= SEQUENCE {
    locationfailurecause            LocationFailureCause,
    ...
}

LocationFailureCause ::= ENUMERATED {
    undefined,
    requestedMethodNotSupported,
    positionMethodFailure,
    periodicLocationMeasurementsNotAvailable,
    ...
}

EarlyFixReport-r12 ::= ENUMERATED {
    noMoreMessages,
    moreMessagesOnTheWay
}

LocationSource-r13 ::= BIT STRING { a-gnss              (0),
                                    wlan                (1),
                                    bt                  (2),
                                    tbs                 (3),
                                    sensor              (4) } (SIZE(1..16))

-- ASN1STOP
-- ASN1START

CommonIEsAbort ::= SEQUENCE {
    abortCause          ENUMERATED {
        undefined,
        stopPeriodicReporting,
        targetDeviceAbort,
        networkAbort,
        ...
    }
}

-- ASN1STOP
-- ASN1START

CommonIEsError ::= SEQUENCE {
    errorCause      ENUMERATED {
        undefined,
        lppMessageHeaderError,
        lppMessageBodyError,
        epduError,
        incorrectDataValue,
        ...
    }
}

-- ASN1STOP
-- ASN1START

OTDOA-ProvideAssistanceData ::= SEQUENCE {
    otdoa-ReferenceCellInfo         OTDOA-ReferenceCellInfo             OPTIONAL,   -- Need ON
    otdoa-NeighbourCellInfo         OTDOA-NeighbourCellInfoList         OPTIONAL,   -- Need ON
    otdoa-Error                     OTDOA-Error                         OPTIONAL,   -- Need ON
    ...,

      otdoa-ReferenceCellInfoNB-r14 OTDOA-ReferenceCellInfoNB-r14       OPTIONAL,   -- Need ON
      otdoa-NeighbourCellInfoNB-r14 OTDOA-NeighbourCellInfoListNB-r14   OPTIONAL    -- Need ON

}

-- ASN1STOP
-- ASN1START

OTDOA-ReferenceCellInfo ::= SEQUENCE {
    physCellId                  INTEGER (0..503),
    cellGlobalId                ECGI                        OPTIONAL,       -- Need ON
    earfcnRef                   ARFCN-ValueEUTRA            OPTIONAL,       -- Cond NotSameAsServ0
    antennaPortConfig           ENUMERATED {ports1-or-2, ports4, ... }
                                                            OPTIONAL,       -- Cond NotSameAsServ1
    cpLength                    ENUMERATED { normal, extended, ... },
    prsInfo                     PRS-Info                    OPTIONAL,       -- Cond PRS
    ...,
     earfcnRef-v9a0           ARFCN-ValueEUTRA-v9a0       OPTIONAL        -- Cond NotSameAsServ2
    ,
     tpId-r14                 INTEGER (0..4095)           OPTIONAL,       -- Need ON
        cpLengthCRS-r14         ENUMERATED { normal, extended, ... }
                                                            OPTIONAL,       -- Cond CRS
        sameMBSFNconfigRef-r14  BOOLEAN                     OPTIONAL,       -- Need ON
        dlBandwidth-r14         ENUMERATED {n6, n15, n25, n50, n75, n100}
                                                            OPTIONAL,       -- Cond NotSameAsServ3
        addPRSconfigRef-r14     SEQUENCE (SIZE (1..maxAddPRSconfig-r14)) OF PRS-Info
                                                            OPTIONAL        -- Need ON

}

maxAddPRSconfig-r14             INTEGER ::= 2

-- ASN1STOP
-- ASN1START

PRS-Info ::= SEQUENCE {
    prs-Bandwidth           ENUMERATED { n6, n15, n25, n50, n75, n100, ... },
    prs-ConfigurationIndex  INTEGER (0..4095),
    numDL-Frames            ENUMERATED {sf-1, sf-2, sf-4, sf-6, ..., sf-add-v1420},
    ...,
    prs-MutingInfo-r9       CHOICE {
        po2-r9                  BIT STRING (SIZE(2)),
        po4-r9                  BIT STRING (SIZE(4)),
        po8-r9                  BIT STRING (SIZE(8)),
        po16-r9                 BIT STRING (SIZE(16)),
        ...,
        po32-v1420              BIT STRING (SIZE(32)),
        po64-v1420              BIT STRING (SIZE(64)),
        po128-v1420             BIT STRING (SIZE(128)),
        po256-v1420             BIT STRING (SIZE(256)),
        po512-v1420             BIT STRING (SIZE(512)),
        po1024-v1420            BIT STRING (SIZE(1024))
    }                                                       OPTIONAL,               -- Need OP
      prsID-r14               INTEGER (0..4095)           OPTIONAL,               -- Need ON
        add-numDL-Frames-r14    INTEGER (1..160)            OPTIONAL,               -- Cond sf-add
        prsOccGroupLen-r14      ENUMERATED {g2, g4, g8, g16, g32, g64, g128,... }
                                                            OPTIONAL,               -- Cond Occ-Grp
        prsHoppingInfo-r14  CHOICE {
            nb2-r14             INTEGER (0.. maxAvailNarrowBands-Minus1-r14),
            nb4-r14             SEQUENCE (SIZE (3))
                                        OF INTEGER (0.. maxAvailNarrowBands-Minus1-r14)
    }                                                       OPTIONAL                -- Cond PRS-FH

}

maxAvailNarrowBands-Minus1-r14      INTEGER ::= 15  -- Maximum number of narrowbands minus 1

-- ASN1STOP
-- ASN1START

OTDOA-NeighbourCellInfoList ::= SEQUENCE (SIZE (1..maxFreqLayers)) OF OTDOA-NeighbourFreqInfo
OTDOA-NeighbourFreqInfo ::= SEQUENCE (SIZE (1..24)) OF OTDOA-NeighbourCellInfoElement

OTDOA-NeighbourCellInfoElement ::= SEQUENCE {
    physCellId                          INTEGER (0..503),
    cellGlobalId                        ECGI                OPTIONAL,       -- Need ON
    earfcn                              ARFCN-ValueEUTRA    OPTIONAL,       -- Cond NotSameAsRef0
    cpLength                            ENUMERATED {normal, extended, ...}
                                                            OPTIONAL,       -- Cond NotSameAsRef1
    prsInfo                             PRS-Info            OPTIONAL,       -- Cond NotSameAsRef2
    antennaPortConfig                   ENUMERATED {ports-1-or-2, ports-4, ...}
                                                            OPTIONAL,       -- Cond NotsameAsRef3
    slotNumberOffset                    INTEGER (0..19)     OPTIONAL,       -- Cond NotSameAsRef4
    prs-SubframeOffset                  INTEGER (0..1279)   OPTIONAL,       -- Cond InterFreq
    expectedRSTD                        INTEGER (0..16383),
    expectedRSTD-Uncertainty            INTEGER (0..1023),
    ...,
     earfcn-v9a0                  ARFCN-ValueEUTRA-v9a0   OPTIONAL        -- Cond NotSameAsRef5
    ,
     tpId-r14                     INTEGER (0..4095)       OPTIONAL,       -- Need ON
        prs-only-tp-r14             ENUMERATED { true }     OPTIONAL,       -- Cond TBS
        cpLengthCRS-r14             ENUMERATED { normal, extended, ... }
                                                            OPTIONAL,       -- Cond CRS
        sameMBSFNconfigNeighbour-r14    BOOLEAN             OPTIONAL,       -- Need ON
        dlBandwidth-r14             ENUMERATED {n6, n15, n25, n50, n75, n100}
                                                            OPTIONAL,       -- Cond NotSameAsRef6
        addPRSconfigNeighbour-r14   SEQUENCE (SIZE (1..maxAddPRSconfig-r14)) OF
                                        Add-PRSconfigNeighbourElement-r14
                                                            OPTIONAL        -- Need ON

}

Add-PRSconfigNeighbourElement-r14 ::= SEQUENCE {
    add-prsInfo-r14                 PRS-Info                OPTIONAL,       -- Cond NotSameAsRef7
    ...
}

maxFreqLayers   INTEGER ::= 3

-- ASN1STOP
-- ASN1START

OTDOA-ReferenceCellInfoNB-r14 ::= SEQUENCE {
    physCellIdNB-r14                INTEGER (0..503)            OPTIONAL,   -- Cond NoPRS-AD1
    cellGlobalIdNB-r14              ECGI                        OPTIONAL,   -- Cond NoPRS-AD2
    carrierFreqRef-r14              CarrierFreq-NB-r14          OPTIONAL,   -- Cond NotSameAsServ1
    earfcn-r14                      ARFCN-ValueEUTRA-r14        OPTIONAL,   -- Cond Inband
    eutra-NumCRS-Ports-r14          ENUMERATED {ports1-or-2, ports4}
                                                                OPTIONAL,   -- Cond NoPRS-AD3
    otdoa-SIB1-NB-repetitions-r14   ENUMERATED { r4, r8, r16 }  OPTIONAL,   -- Cond NotSameAsServ2
    nprsInfo-r14                    PRS-Info-NB-r14             OPTIONAL,   -- Cond NPRS
    ...
}

-- ASN1STOP
-- ASN1START

PRS-Info-NB-r14 ::= SEQUENCE (SIZE (1..maxCarrier-r14)) OF NPRS-Info-r14

NPRS-Info-r14 ::= SEQUENCE {
    operationModeInfoNPRS-r14   ENUMERATED { inband, standalone },
    nprs-carrier-r14            CarrierFreq-NB-r14  OPTIONAL,   -- Cond Standalone/Guardband
    nprsSequenceInfo-r14        INTEGER (0..174)    OPTIONAL,   -- Cond Inband
    nprsID-r14                  INTEGER (0..4095)   OPTIONAL,   -- Cond NPRS-ID
    partA-r14                   SEQUENCE {
        nprsBitmap-r14          CHOICE {
            subframePattern10-r14   BIT STRING (SIZE (10)),
            subframePattern40-r14   BIT STRING (SIZE (40))
        },
        nprs-MutingInfoA-r14    CHOICE {
            po2-r14                 BIT STRING (SIZE(2)),
            po4-r14                 BIT STRING (SIZE(4)),
            po8-r14                 BIT STRING (SIZE(8)),
            po16-r14                BIT STRING (SIZE(16)),
            ...
        }                                                           OPTIONAL,       -- Cond MutingA
        ...
    }                                                               OPTIONAL,       -- Cond PartA
    partB-r14                   SEQUENCE {
        nprs-Period-r14         ENUMERATED { ms160, ms320, ms640, ms1280, ... },
        nprs-startSF-r14        ENUMERATED { zero, one-eighth, two-eighths, three-eighths,
                                             four-eighths, five-eighths, six-eighths,
                                             seven-eighths, ...},
        nprs-NumSF-r14          ENUMERATED { sf10, sf20, sf40, sf80, sf160, sf320,
                                             sf640, sf1280, ...},
        nprs-MutingInfoB-r14    CHOICE {
            po2-r14                 BIT STRING (SIZE(2)),
            po4-r14                 BIT STRING (SIZE(4)),
            po8-r14                 BIT STRING (SIZE(8)),
            po16-r14                BIT STRING (SIZE(16)),
            ...
        }                                                           OPTIONAL,       -- Cond MutingB
        ...
    }                                                               OPTIONAL,       -- Cond PartB
    ...
}

maxCarrier-r14  INTEGER ::= 5

-- ASN1STOP
-- ASN1START

OTDOA-NeighbourCellInfoListNB-r14 ::= SEQUENCE (SIZE (1..maxCells-r14)) OF
                                                        OTDOA-NeighbourCellInfoNB-r14

OTDOA-NeighbourCellInfoNB-r14 ::= SEQUENCE {
    physCellIdNB-r14                INTEGER (0..503)        OPTIONAL,       -- Cond NoPRS-AD1
    cellGlobalIdNB-r14              ECGI                    OPTIONAL,       -- Cond NoPRS-AD2
    carrierFreq-r14                 CarrierFreq-NB-r14      OPTIONAL,       -- Cond NotSameAsRef1
    earfcn-r14                      ARFCN-ValueEUTRA-r14    OPTIONAL,       -- Cond Inband
    eutra-NumCRS-Ports-r14          ENUMERATED {ports-1-or-2, ports-4, ...}
                                                            OPTIONAL,       -- Cond NotsameAsRef2
    otdoa-SIB1-NB-repetitions-r14   ENUMERATED { r4, r8, r16 }
                                                            OPTIONAL,       -- Cond NotSameAsRef3
    nprsInfo-r14                    PRS-Info-NB-r14         OPTIONAL,       -- Cond NotsameAsRef4
    nprs-slotNumberOffset-r14       INTEGER (0..19)         OPTIONAL,       -- Cond NotsameAsRef5
    nprs-SFN-Offset-r14             INTEGER (0..63)         OPTIONAL,       -- Cond NotsameAsRef6
    nprs-SubframeOffset-r14         INTEGER (0..1279)       OPTIONAL,       -- Need OP
    expectedRSTD-r14                INTEGER (0..16383)      OPTIONAL,       -- Cond NoPRS-AD3
    expectedRSTD-Uncertainty-r14    INTEGER (0..1023)       OPTIONAL,       -- Cond NoPRS-AD3
    prsNeighbourCellIndex-r14       INTEGER (1..72)         OPTIONAL,       -- Cond PRS-AD
    ...
}

maxCells-r14    INTEGER ::= 72

-- ASN1STOP
-- ASN1START

OTDOA-RequestAssistanceData ::= SEQUENCE {
    physCellId      INTEGER (0..503),
    ...,

      adType-r14    BIT STRING { prs (0), nprs (1) } (SIZE (1..8))      OPTIONAL

}

-- ASN1STOP
-- ASN1START

OTDOA-ProvideLocationInformation ::= SEQUENCE {
    otdoaSignalMeasurementInformation   OTDOA-SignalMeasurementInformation  OPTIONAL,
    otdoa-Error                         OTDOA-Error                         OPTIONAL,
    ...,

        otdoaSignalMeasurementInformation-NB-r14    OTDOA-SignalMeasurementInformation-NB-r14   OPTIONAL

}

-- ASN1STOP
-- ASN1START

OTDOA-SignalMeasurementInformation ::= SEQUENCE {
    systemFrameNumber       BIT STRING (SIZE (10)),
    physCellIdRef           INTEGER (0..503),
    cellGlobalIdRef         ECGI                    OPTIONAL,
    earfcnRef               ARFCN-ValueEUTRA        OPTIONAL,       -- Cond NotSameAsRef0
    referenceQuality        OTDOA-MeasQuality       OPTIONAL,
    neighbourMeasurementList    NeighbourMeasurementList,
    ...,
     earfcnRef-v9a0       ARFCN-ValueEUTRA-v9a0   OPTIONAL        -- Cond NotSameAsRef1
    ,
     tpIdRef-r14          INTEGER (0..4095)       OPTIONAL,       -- Cond ProvidedByServer0
        prsIdRef-r14        INTEGER (0..4095)       OPTIONAL,       -- Cond ProvidedByServer1
        additionalPathsRef-r14
                            AdditionalPathList-r14  OPTIONAL,
        nprsIdRef-r14       INTEGER (0..4095)       OPTIONAL,       -- Cond ProvidedByServer2
        carrierFreqOffsetNB-Ref-r14
                            CarrierFreqOffsetNB-r14 OPTIONAL,       -- Cond NB-IoT
        hyperSFN-r14        BIT STRING (SIZE (10))  OPTIONAL        -- Cond H-SFN

}

NeighbourMeasurementList ::= SEQUENCE (SIZE(1..24)) OF NeighbourMeasurementElement

NeighbourMeasurementElement ::= SEQUENCE {
    physCellIdNeighbour     INTEGER (0..503),
    cellGlobalIdNeighbour   ECGI                    OPTIONAL,
    earfcnNeighbour         ARFCN-ValueEUTRA        OPTIONAL,       -- Cond NotSameAsRef2
    rstd                    INTEGER (0..12711),
    rstd-Quality            OTDOA-MeasQuality,
    ...,
     earfcnNeighbour-v9a0 ARFCN-ValueEUTRA-v9a0   OPTIONAL        -- Cond NotSameAsRef3
    ,
     tpIdNeighbour-r14    INTEGER (0..4095)       OPTIONAL,       -- Cond ProvidedByServer0
        prsIdNeighbour-r14  INTEGER (0..4095)       OPTIONAL,       -- Cond ProvidedByServer1
        delta-rstd-r14      INTEGER (0..5)          OPTIONAL,
        additionalPathsNeighbour-r14
                            AdditionalPathList-r14  OPTIONAL,
        nprsIdNeighbour-r14 INTEGER (0..4095)       OPTIONAL,       -- Cond ProvidedByServer2
        carrierFreqOffsetNB-Neighbour-r14
                            CarrierFreqOffsetNB-r14 OPTIONAL        -- Cond NB-IoT

}

AdditionalPathList-r14 ::= SEQUENCE (SIZE(1..maxPaths-r14)) OF AdditionalPath-r14

maxPaths-r14    INTEGER ::= 2

-- ASN1STOP
-- ASN1START

OTDOA-SignalMeasurementInformation-NB-r14 ::= SEQUENCE {
    systemFrameNumber-r14           BIT STRING (SIZE (10)),
    physCellIdRef-r14               INTEGER (0..503),
    cellGlobalIdRef-r14             ECGI                    OPTIONAL,
    earfcnRef-r14                   ARFCN-ValueEUTRA-r14    OPTIONAL,   -- Cond NotSameAsRef0
    referenceQuality-r14            OTDOA-MeasQuality       OPTIONAL,
    neighbourMeasurementList-r14    NeighbourMeasurementList-NB-r14,
    tpIdRef-r14                     INTEGER (0..4095)       OPTIONAL,   -- Cond ProvidedByServer0
    prsIdRef-r14                    INTEGER (0..4095)       OPTIONAL,   -- Cond ProvidedByServer1
    additionalPathsRef-r14          AdditionalPathList-r14  OPTIONAL,
    nprsIdRef-r14                   INTEGER (0..4095)       OPTIONAL,   -- Cond ProvidedByServer2
    carrierFreqOffsetNB-Ref-r14     CarrierFreqOffsetNB-r14 OPTIONAL,   -- Cond NB-IoT
    hyperSFN-r14                    BIT STRING (SIZE (10))  OPTIONAL,   -- Cond H-SFN
    ...
}

NeighbourMeasurementList-NB-r14 ::= SEQUENCE (SIZE(1..24)) OF NeighbourMeasurementElement-NB-r14

NeighbourMeasurementElement-NB-r14 ::= SEQUENCE {
    physCellIdNeighbour-r14     INTEGER (0..503),
    cellGlobalIdNeighbour-r14   ECGI                    OPTIONAL,
    earfcnNeighbour-r14         ARFCN-ValueEUTRA-r14    OPTIONAL,       -- Cond NotSameAsRef2
    rstd-r14                    INTEGER (0..12711),
    rstd-Quality-r14            OTDOA-MeasQuality,
    tpIdNeighbour-r14           INTEGER (0..4095)       OPTIONAL,       -- Cond ProvidedByServer0
    prsIdNeighbour-r14          INTEGER (0..4095)       OPTIONAL,       -- Cond ProvidedByServer1
    delta-rstd-r14              INTEGER (0..5)          OPTIONAL,
    additionalPathsNeighbour-r14
                                AdditionalPathList-r14  OPTIONAL,
    nprsIdNeighbour-r14         INTEGER (0..4095)       OPTIONAL,       -- Cond ProvidedByServer2
    carrierFreqOffsetNB-Neighbour-r14
                                CarrierFreqOffsetNB-r14 OPTIONAL,       -- Cond NB-IoT
    ...
}

-- ASN1STOP
-- ASN1START

OTDOA-MeasQuality ::= SEQUENCE {
    error-Resolution        BIT STRING (SIZE (2)),
    error-Value             BIT STRING (SIZE (5)),
    error-NumSamples        BIT STRING (SIZE (3))               OPTIONAL,
    ...
}

-- ASN1STOP
-- ASN1START

AdditionalPath-r14 ::= SEQUENCE {
    relativeTimeDifference-r14  INTEGER (-256..255),
    path-Quality-r14            OTDOA-MeasQuality               OPTIONAL,
    ...
}

-- ASN1STOP
-- ASN1START

OTDOA-RequestLocationInformation ::= SEQUENCE {
    assistanceAvailability      BOOLEAN,
    ...,

        multipathRSTD-r14       ENUMERATED { requested }    OPTIONAL,       -- Need ON
        maxNoOfRSTDmeas-r14     INTEGER (1..32)             OPTIONAL        -- Need ON

}

-- ASN1STOP
-- ASN1START

OTDOA-ProvideCapabilities ::= SEQUENCE {
    otdoa-Mode      BIT STRING {    ue-assisted         (0),
                                    ue-assisted-NB-r14  (1) } (SIZE (1..8)),
    ...,
    supportedBandListEUTRA      SEQUENCE (SIZE (1..maxBands)) OF SupportedBandEUTRA     OPTIONAL,
    supportedBandListEUTRA-v9a0 SEQUENCE (SIZE (1..maxBands)) OF SupportedBandEUTRA-v9a0
                                                                                        OPTIONAL,
    interFreqRSTDmeasurement-r10        ENUMERATED { supported }                        OPTIONAL,
    additionalNeighbourCellInfoList-r10 ENUMERATED { supported }                        OPTIONAL,
    prs-id-r14                          ENUMERATED { supported }                        OPTIONAL,
    tp-separation-via-muting-r14        ENUMERATED { supported }                        OPTIONAL,
    additional-prs-config-r14           ENUMERATED { supported }                        OPTIONAL,
    prs-based-tbs-r14                   ENUMERATED { supported }                        OPTIONAL,
    additionalPathsReport-r14           ENUMERATED { supported }                        OPTIONAL,
    densePrsConfig-r14                  ENUMERATED { supported }                        OPTIONAL,
    maxSupportedPrsBandwidth-r14        ENUMERATED { n6, n15, n25, n50, n75, n100, ...} OPTIONAL,
    prsOccGroup-r14                     ENUMERATED { supported }                        OPTIONAL,
    prsFrequencyHopping-r14             ENUMERATED { supported }                        OPTIONAL,
    maxSupportedPrsConfigs-r14          ENUMERATED { c2, c3 }                           OPTIONAL,
    periodicalReporting-r14             ENUMERATED { supported }                        OPTIONAL,
    multiPrbNprs-r14                    ENUMERATED { supported }                        OPTIONAL,
    idleStateForMeasurements-r14        ENUMERATED { required }                         OPTIONAL,
    numberOfRXantennas-r14              ENUMERATED { rx1, ... }                         OPTIONAL
}

maxBands INTEGER ::= 64

SupportedBandEUTRA ::= SEQUENCE {
    bandEUTRA                           INTEGER (1..maxFBI)
}

SupportedBandEUTRA-v9a0 ::=     SEQUENCE {
    bandEUTRA-v9a0                      INTEGER (maxFBI-Plus1..maxFBI2)     OPTIONAL
}

maxFBI                              INTEGER ::= 64  -- Maximum value of frequency band indicator
maxFBI-Plus1                        INTEGER ::= 65  -- lowest value extended FBI range
maxFBI2                             INTEGER ::= 256 -- highest value extended FBI range

-- ASN1STOP
-- ASN1START

OTDOA-RequestCapabilities ::= SEQUENCE {
    ...
}

-- ASN1STOP
-- ASN1START

OTDOA-Error ::= CHOICE {
    locationServerErrorCauses       OTDOA-LocationServerErrorCauses,
    targetDeviceErrorCauses         OTDOA-TargetDeviceErrorCauses,
    ...
}

-- ASN1STOP
-- ASN1START

OTDOA-LocationServerErrorCauses ::= SEQUENCE {
    cause       ENUMERATED  {   undefined,
                                assistanceDataNotSupportedByServer,
                                assistanceDataSupportedButCurrentlyNotAvailableByServer,
                                ...
                            },
    ...
}

-- ASN1STOP
-- ASN1START

OTDOA-TargetDeviceErrorCauses ::= SEQUENCE {
    cause       ENUMERATED {    undefined,
                                assistance-data-missing,
                                unableToMeasureReferenceCell,
                                unableToMeasureAnyNeighbourCell,
                                attemptedButUnableToMeasureSomeNeighbourCells,
                                ...
                            },
    ...
}

-- ASN1STOP
-- ASN1START

A-GNSS-ProvideAssistanceData ::= SEQUENCE {
    gnss-CommonAssistData           GNSS-CommonAssistData               OPTIONAL,   -- Need ON
    gnss-GenericAssistData          GNSS-GenericAssistData              OPTIONAL,   -- Need ON
    gnss-Error                      A-GNSS-Error                        OPTIONAL,   -- Need ON
    ...
}

-- ASN1STOP
-- ASN1START

GNSS-CommonAssistData ::= SEQUENCE {
    gnss-ReferenceTime              GNSS-ReferenceTime                  OPTIONAL,   -- Need ON
    gnss-ReferenceLocation          GNSS-ReferenceLocation              OPTIONAL,   -- Need ON
    gnss-IonosphericModel           GNSS-IonosphericModel               OPTIONAL,   -- Need ON
    gnss-EarthOrientationParameters GNSS-EarthOrientationParameters     OPTIONAL,   -- Need ON
    ...
}

-- ASN1STOP
-- ASN1START

GNSS-GenericAssistData ::= SEQUENCE (SIZE (1..16)) OF GNSS-GenericAssistDataElement

GNSS-GenericAssistDataElement ::= SEQUENCE {
    gnss-ID                         GNSS-ID,
    sbas-ID                         SBAS-ID                         OPTIONAL, -- Cond GNSS-ID-SBAS
    gnss-TimeModels                 GNSS-TimeModelList              OPTIONAL,   -- Need ON
    gnss-DifferentialCorrections    GNSS-DifferentialCorrections    OPTIONAL,   -- Need ON
    gnss-NavigationModel            GNSS-NavigationModel            OPTIONAL,   -- Need ON
    gnss-RealTimeIntegrity          GNSS-RealTimeIntegrity          OPTIONAL,   -- Need ON
    gnss-DataBitAssistance          GNSS-DataBitAssistance          OPTIONAL,   -- Need ON
    gnss-AcquisitionAssistance      GNSS-AcquisitionAssistance      OPTIONAL,   -- Need ON
    gnss-Almanac                    GNSS-Almanac                    OPTIONAL,   -- Need ON
    gnss-UTC-Model                  GNSS-UTC-Model                  OPTIONAL,   -- Need ON
    gnss-AuxiliaryInformation       GNSS-AuxiliaryInformation       OPTIONAL,   -- Need ON
    ...,

        bds-DifferentialCorrections-r12
                                    BDS-DifferentialCorrections-r12 OPTIONAL,   -- Cond GNSS-ID-BDS
        bds-GridModel-r12           BDS-GridModelParameter-r12      OPTIONAL    -- Cond GNSS-ID-BDS

}

-- ASN1STOP
-- ASN1START

GNSS-ReferenceTime ::= SEQUENCE  {
    gnss-SystemTime             GNSS-SystemTime,
    referenceTimeUnc            INTEGER (0..127)                    OPTIONAL,   -- Cond noFTA
    gnss-ReferenceTimeForCells  SEQUENCE (SIZE (1..16)) OF
                                    GNSS-ReferenceTimeForOneCell    OPTIONAL,   -- Need ON
    ...
}

GNSS-ReferenceTimeForOneCell  ::= SEQUENCE {
    networkTime                 NetworkTime,
    referenceTimeUnc            INTEGER (0..127),
    bsAlign                     ENUMERATED {true}   OPTIONAL,
    ...
}

-- ASN1STOP
-- ASN1START

GNSS-SystemTime ::= SEQUENCE {
    gnss-TimeID                     GNSS-ID,
    gnss-DayNumber                  INTEGER (0..32767),
    gnss-TimeOfDay                  INTEGER (0..86399),
    gnss-TimeOfDayFrac-msec         INTEGER (0..999)        OPTIONAL,   -- Need ON
    notificationOfLeapSecond        BIT STRING (SIZE(2))    OPTIONAL,   -- Cond gnss-TimeID-glonass
    gps-TOW-Assist                  GPS-TOW-Assist          OPTIONAL,   -- Cond gnss-TimeID-gps
    ...
}

-- ASN1STOP
-- ASN1START

GPS-TOW-Assist ::= SEQUENCE (SIZE(1..64)) OF GPS-TOW-AssistElement

GPS-TOW-AssistElement ::= SEQUENCE {
    satelliteID     INTEGER (1..64),
    tlmWord         INTEGER (0..16383),
    antiSpoof       INTEGER (0..1),
    alert           INTEGER (0..1),
    tlmRsvdBits     INTEGER (0..3),
    ...
}

-- ASN1STOP
-- ASN1START

NetworkTime ::= SEQUENCE {
    secondsFromFrameStructureStart              INTEGER(0..12533),
    fractionalSecondsFromFrameStructureStart    INTEGER(0..3999999),
    frameDrift                                  INTEGER (-64..63)   OPTIONAL,   -- Cond GNSSsynch
    cellID      CHOICE {
                eUTRA       SEQUENCE {
                            physCellId          INTEGER (0..503),
                            cellGlobalIdEUTRA   CellGlobalIdEUTRA-AndUTRA   OPTIONAL,   -- Need ON
                            earfcn              ARFCN-ValueEUTRA,
                            ...,
                             earfcn-v9a0      ARFCN-ValueEUTRA-v9a0 OPTIONAL  -- Cond EARFCN-max

                            },
                uTRA        SEQUENCE {
                            mode    CHOICE {
                                    fdd     SEQUENCE {
                                            primary-CPICH-Info  INTEGER (0..511),
                                            ...
                                            },
                                    tdd     SEQUENCE {
                                            cellParameters      INTEGER (0..127),
                                            ...
                                            }
                                    },
                            cellGlobalIdUTRA    CellGlobalIdEUTRA-AndUTRA   OPTIONAL,   -- Need ON
                            uarfcn              ARFCN-ValueUTRA,
                            ...
                            },
                gSM         SEQUENCE {
                            bcchCarrier         INTEGER (0..1023),
                            bsic                INTEGER (0..63),
                            cellGlobalIdGERAN   CellGlobalIdGERAN           OPTIONAL,   -- Need ON
                            ...
                            },
                ...,
                nBIoT-r14   SEQUENCE {
                            nbPhysCellId-r14    INTEGER (0..503),
                            nbCellGlobalId-r14  ECGI                        OPTIONAL,   -- Need ON
                            nbCarrierFreq-r14   CarrierFreq-NB-r14,
                            ...
                            }
                },
    ...
}

-- ASN1STOP
-- ASN1START

GNSS-ReferenceLocation ::= SEQUENCE {
        threeDlocation          EllipsoidPointWithAltitudeAndUncertaintyEllipsoid,
        ...
}

-- ASN1STOP
-- ASN1START

GNSS-IonosphericModel ::= SEQUENCE {
    klobucharModel          KlobucharModelParameter     OPTIONAL,   -- Need ON
    neQuickModel            NeQuickModelParameter       OPTIONAL,   -- Need ON
    ...
}

-- ASN1STOP
-- ASN1START

KlobucharModelParameter ::= SEQUENCE {
    dataID          BIT STRING (SIZE (2)),
    alfa0           INTEGER (-128..127),
    alfa1           INTEGER (-128..127),
    alfa2           INTEGER (-128..127),
    alfa3           INTEGER (-128..127),
    beta0           INTEGER (-128..127),
    beta1           INTEGER (-128..127),
    beta2           INTEGER (-128..127),
    beta3           INTEGER (-128..127),
    ...
}

-- ASN1STOP
-- ASN1START

NeQuickModelParameter ::= SEQUENCE {
    ai0             INTEGER (0..2047),
    ai1             INTEGER (-1024..1023),
    ai2             INTEGER (-8192..8191),
    ionoStormFlag1  INTEGER (0..1)      OPTIONAL,   -- Need OP
    ionoStormFlag2  INTEGER (0..1)      OPTIONAL,   -- Need OP
    ionoStormFlag3  INTEGER (0..1)      OPTIONAL,   -- Need OP
    ionoStormFlag4  INTEGER (0..1)      OPTIONAL,   -- Need OP
    ionoStormFlag5  INTEGER (0..1)      OPTIONAL,   -- Need OP
    ...
}

-- ASN1STOP
-- ASN1START

GNSS-EarthOrientationParameters ::= SEQUENCE {
    teop                INTEGER (0..65535),
    pmX                 INTEGER (-1048576..1048575),
    pmXdot              INTEGER (-16384..16383),
    pmY                 INTEGER (-1048576..1048575),
    pmYdot              INTEGER (-16384..16383),
    deltaUT1            INTEGER (-1073741824..1073741823),
    deltaUT1dot         INTEGER (-262144..262143),
    ...
}

-- ASN1STOP
-- ASN1START

GNSS-TimeModelList ::= SEQUENCE (SIZE (1..15)) OF GNSS-TimeModelElement

GNSS-TimeModelElement ::= SEQUENCE {
    gnss-TimeModelRefTime       INTEGER (0..65535),
    tA0                         INTEGER (-67108864..67108863),
    tA1                         INTEGER (-4096..4095)                   OPTIONAL,   -- Need ON
    tA2                         INTEGER (-64..63)                       OPTIONAL,   -- Need ON
    gnss-TO-ID                  INTEGER (1..15),
    weekNumber                  INTEGER (0..8191)                       OPTIONAL,   -- Need ON
    deltaT                      INTEGER (-128..127)                     OPTIONAL,   -- Need ON
    ...
}

-- ASN1STOP
-- ASN1START

GNSS-DifferentialCorrections ::= SEQUENCE {
    dgnss-RefTime       INTEGER (0..3599),
    dgnss-SgnTypeList   DGNSS-SgnTypeList,
    ...
}

DGNSS-SgnTypeList ::= SEQUENCE (SIZE (1..3)) OF DGNSS-SgnTypeElement

DGNSS-SgnTypeElement ::= SEQUENCE {
    gnss-SignalID        GNSS-SignalID,
    gnss-StatusHealth    INTEGER (0..7),
    dgnss-SatList        DGNSS-SatList,
    ...
}

DGNSS-SatList ::= SEQUENCE (SIZE (1..64)) OF DGNSS-CorrectionsElement

DGNSS-CorrectionsElement ::= SEQUENCE {
    svID                SV-ID,
    iod                 BIT STRING (SIZE(11)),
    udre                INTEGER (0..3),
    pseudoRangeCor      INTEGER (-2047..2047),
    rangeRateCor        INTEGER (-127..127),
    udreGrowthRate      INTEGER (0..7)          OPTIONAL,   -- Need ON
    udreValidityTime    INTEGER (0..7)          OPTIONAL,   -- Need ON
    ...
}

-- ASN1STOP
-- ASN1START

GNSS-NavigationModel ::= SEQUENCE {
    nonBroadcastIndFlag     INTEGER (0..1),
    gnss-SatelliteList      GNSS-NavModelSatelliteList,
    ...
}

GNSS-NavModelSatelliteList ::= SEQUENCE (SIZE(1..64)) OF GNSS-NavModelSatelliteElement

GNSS-NavModelSatelliteElement ::= SEQUENCE {
    svID                SV-ID,
    svHealth            BIT STRING (SIZE(8)),
    iod                 BIT STRING (SIZE(11)),
    gnss-ClockModel     GNSS-ClockModel,
    gnss-OrbitModel     GNSS-OrbitModel,
    ...,
      svHealthExt-v1240 BIT STRING (SIZE(4))          OPTIONAL        -- Need ON

}

GNSS-ClockModel ::= CHOICE {
    standardClockModelList  StandardClockModelList,         -- Model-1
    nav-ClockModel          NAV-ClockModel,                 -- Model-2
    cnav-ClockModel         CNAV-ClockModel,                -- Model-3
    glonass-ClockModel      GLONASS-ClockModel,             -- Model-4
    sbas-ClockModel         SBAS-ClockModel,                -- Model-5
    ...,
    bds-ClockModel-r12      BDS-ClockModel-r12              -- Model-6
}

GNSS-OrbitModel ::= CHOICE {
    keplerianSet            NavModelKeplerianSet,           -- Model-1
    nav-KeplerianSet        NavModelNAV-KeplerianSet,       -- Model-2
    cnav-KeplerianSet       NavModelCNAV-KeplerianSet,      -- Model-3
    glonass-ECEF            NavModel-GLONASS-ECEF,          -- Model-4
    sbas-ECEF               NavModel-SBAS-ECEF,             -- Model-5
    ...,
    bds-KeplerianSet-r12    NavModel-BDS-KeplerianSet-r12   -- Model-6
}

-- ASN1STOP
-- ASN1START

StandardClockModelList ::= SEQUENCE (SIZE(1..2)) OF StandardClockModelElement

StandardClockModelElement ::= SEQUENCE {
    stanClockToc            INTEGER (0..16383),
    stanClockAF2            INTEGER (-32..31),
    stanClockAF1            INTEGER (-1048576..1048575),
    stanClockAF0            INTEGER (-1073741824..1073741823),
    stanClockTgd            INTEGER (-512..511)             OPTIONAL,   -- Need ON
    sisa                    INTEGER (0..255),
    stanModelID             INTEGER (0..1)                  OPTIONAL,   -- Need ON
    ...
}

-- ASN1STOP
-- ASN1START

NAV-ClockModel ::= SEQUENCE {
    navToc          INTEGER (0..37799),
    navaf2          INTEGER (-128..127),
    navaf1          INTEGER (-32768..32767),
    navaf0          INTEGER (-2097152..2097151),
    navTgd          INTEGER (-128..127),
    ...
}

-- ASN1STOP
-- ASN1START

CNAV-ClockModel ::= SEQUENCE {
    cnavToc         INTEGER (0..2015),
    cnavTop         INTEGER (0..2015),
    cnavURA0        INTEGER (-16..15),
    cnavURA1        INTEGER (0..7),
    cnavURA2        INTEGER (0..7),
    cnavAf2         INTEGER (-512..511),
    cnavAf1         INTEGER (-524288..524287),
    cnavAf0         INTEGER (-33554432..33554431),
    cnavTgd         INTEGER (-4096..4095),
    cnavISCl1cp     INTEGER (-4096..4095)           OPTIONAL,   -- Need ON
    cnavISCl1cd     INTEGER (-4096..4095)           OPTIONAL,   -- Need ON
    cnavISCl1ca     INTEGER (-4096..4095)           OPTIONAL,   -- Need ON
    cnavISCl2c      INTEGER (-4096..4095)           OPTIONAL,   -- Need ON
    cnavISCl5i5     INTEGER (-4096..4095)           OPTIONAL,   -- Need ON
    cnavISCl5q5     INTEGER (-4096..4095)           OPTIONAL,   -- Need ON
    ...
}

-- ASN1STOP
-- ASN1START

GLONASS-ClockModel ::= SEQUENCE {
    gloTau          INTEGER (-2097152..2097151),
    gloGamma        INTEGER (-1024..1023),
    gloDeltaTau     INTEGER (-16..15)               OPTIONAL,   -- Need ON
    ...
}

-- ASN1STOP
-- ASN1START

SBAS-ClockModel ::= SEQUENCE {
    sbasTo          INTEGER (0..5399),
    sbasAgfo        INTEGER (-2048..2047),
    sbasAgf1        INTEGER (-128..127),
    ...
}

-- ASN1STOP
-- ASN1START

BDS-ClockModel-r12 ::= SEQUENCE {
    bdsAODC-r12         INTEGER (0..31),
    bdsToc-r12          INTEGER (0..131071),
    bdsA0-r12           INTEGER (-8388608..8388607),
    bdsA1-r12           INTEGER (-2097152..2097151),
    bdsA2-r12           INTEGER (-1024..1023),
    bdsTgd1-r12         INTEGER (-512..511),
    ...
}

-- ASN1STOP
-- ASN1START

NavModelKeplerianSet ::= SEQUENCE {
    keplerToe        INTEGER (0 .. 16383),
    keplerW          INTEGER (-2147483648..2147483647),
    keplerDeltaN     INTEGER (-32768..32767),
    keplerM0         INTEGER (-2147483648..2147483647),
    keplerOmegaDot   INTEGER (-8388608.. 8388607),
    keplerE          INTEGER (0..4294967295),
    keplerIDot       INTEGER (-8192..8191),
    keplerAPowerHalf INTEGER (0.. 4294967295),
    keplerI0         INTEGER (-2147483648..2147483647),
    keplerOmega0     INTEGER (-2147483648..2147483647),
    keplerCrs        INTEGER (-32768..32767),
    keplerCis        INTEGER (-32768..32767),
    keplerCus        INTEGER (-32768..32767),
    keplerCrc        INTEGER (-32768..32767),
    keplerCic        INTEGER (-32768..32767),
    keplerCuc        INTEGER (-32768..32767),
    ...
}

-- ASN1STOP
-- ASN1START

NavModelNAV-KeplerianSet ::= SEQUENCE {
    navURA          INTEGER (0..15),
    navFitFlag      INTEGER (0..1),
    navToe          INTEGER (0..37799),
    navOmega        INTEGER (-2147483648..2147483647),
    navDeltaN       INTEGER (-32768..32767),
    navM0           INTEGER (-2147483648..2147483647),
    navOmegaADot    INTEGER (-8388608..8388607),
    navE            INTEGER (0..4294967295),
    navIDot         INTEGER (-8192..8191),
    navAPowerHalf   INTEGER (0..4294967295),
    navI0           INTEGER (-2147483648..2147483647),
    navOmegaA0      INTEGER (-2147483648..2147483647),
    navCrs          INTEGER (-32768..32767),
    navCis          INTEGER (-32768..32767),
    navCus          INTEGER (-32768..32767),
    navCrc          INTEGER (-32768..32767),
    navCic          INTEGER (-32768..32767),
    navCuc          INTEGER (-32768..32767),
    addNAVparam     SEQUENCE {
        ephemCodeOnL2   INTEGER (0..3),
        ephemL2Pflag    INTEGER (0..1),
        ephemSF1Rsvd    SEQUENCE {
            reserved1       INTEGER (0..8388607),   -- 23-bit field
            reserved2       INTEGER (0..16777215),  -- 24-bit field
            reserved3       INTEGER (0..16777215),  -- 24-bit field
            reserved4       INTEGER (0..65535)      -- 16-bit field
        },
        ephemAODA       INTEGER (0..31)
    }   OPTIONAL,   -- Need ON
    ...
}

-- ASN1STOP
-- ASN1START

NavModelCNAV-KeplerianSet ::= SEQUENCE {
    cnavTop             INTEGER (0..2015),
    cnavURAindex        INTEGER (-16..15),
    cnavDeltaA          INTEGER (-33554432..33554431),
    cnavAdot            INTEGER (-16777216..16777215),
    cnavDeltaNo         INTEGER (-65536..65535),
    cnavDeltaNoDot      INTEGER (-4194304..4194303),
    cnavMo              INTEGER (-4294967296..4294967295),
    cnavE               INTEGER (0..8589934591),
    cnavOmega           INTEGER (-4294967296..4294967295),
    cnavOMEGA0          INTEGER (-4294967296..4294967295),
    cnavDeltaOmegaDot   INTEGER (-65536..65535),
    cnavIo              INTEGER (-4294967296..4294967295),
    cnavIoDot           INTEGER (-16384..16383),
    cnavCis             INTEGER (-32768..32767),
    cnavCic             INTEGER (-32768..32767),
    cnavCrs             INTEGER (-8388608..8388607),
    cnavCrc             INTEGER (-8388608..8388607),
    cnavCus             INTEGER (-1048576..1048575),
    cnavCuc             INTEGER (-1048576..1048575),
    ...
}

-- ASN1STOP
-- ASN1START

NavModel-GLONASS-ECEF ::= SEQUENCE {
    gloEn               INTEGER (0..31),
    gloP1               BIT STRING (SIZE(2)),
    gloP2               BOOLEAN,
    gloM                INTEGER (0..3),
    gloX                INTEGER (-67108864..67108863),
    gloXdot             INTEGER (-8388608..8388607),
    gloXdotdot          INTEGER (-16..15),
    gloY                INTEGER (-67108864..67108863),
    gloYdot             INTEGER (-8388608..8388607),
    gloYdotdot          INTEGER (-16..15),
    gloZ                INTEGER (-67108864..67108863),
    gloZdot             INTEGER (-8388608..8388607),
    gloZdotdot          INTEGER (-16..15),
    ...
}

-- ASN1STOP
-- ASN1START

NavModel-SBAS-ECEF ::= SEQUENCE {
    sbasTo              INTEGER (0..5399)                   OPTIONAL,   -- Cond ClockModel
    sbasAccuracy        BIT STRING (SIZE(4)),
    sbasXg              INTEGER (-536870912..536870911),
    sbasYg              INTEGER (-536870912..536870911),
    sbasZg              INTEGER (-16777216..16777215),
    sbasXgDot           INTEGER (-65536..65535),
    sbasYgDot           INTEGER (-65536..65535),
    sbasZgDot           INTEGER (-131072..131071),
    sbasXgDotDot        INTEGER (-512..511),
    sbagYgDotDot        INTEGER (-512..511),
    sbasZgDotDot        INTEGER (-512..511),
    ...
}

-- ASN1STOP
-- ASN1START

NavModel-BDS-KeplerianSet-r12 ::= SEQUENCE {
    bdsAODE-r12             INTEGER (0..31),
    bdsURAI-r12             INTEGER (0..15),
    bdsToe-r12              INTEGER (0..131071),
    bdsAPowerHalf-r12       INTEGER (0..4294967295),
    bdsE-r12                INTEGER (0..4294967295),
    bdsW-r12                INTEGER (-2147483648..2147483647),
    bdsDeltaN-r12           INTEGER (-32768..32767),
    bdsM0-r12               INTEGER (-2147483648..2147483647),
    bdsOmega0-r12           INTEGER (-2147483648..2147483647),
    bdsOmegaDot-r12         INTEGER (-8388608..8388607),
    bdsI0-r12               INTEGER (-2147483648..2147483647),
    bdsIDot-r12             INTEGER (-8192..8191),
    bdsCuc-r12              INTEGER (-131072..131071),
    bdsCus-r12              INTEGER (-131072..131071),
    bdsCrc-r12              INTEGER (-131072..131071),
    bdsCrs-r12              INTEGER (-131072..131071),
    bdsCic-r12              INTEGER (-131072..131071),
    bdsCis-r12              INTEGER (-131072..131071),
    ...
}

-- ASN1STOP
-- ASN1START

GNSS-RealTimeIntegrity ::= SEQUENCE {
    gnss-BadSignalList  GNSS-BadSignalList,
    ...
}

GNSS-BadSignalList ::= SEQUENCE (SIZE(1..64)) OF BadSignalElement

BadSignalElement ::= SEQUENCE {
    badSVID             SV-ID,
    badSignalID         GNSS-SignalIDs  OPTIONAL,   -- Need OP
    ...
}

-- ASN1STOP
-- ASN1START

GNSS-DataBitAssistance ::= SEQUENCE {
    gnss-TOD                INTEGER (0..3599),
    gnss-TODfrac            INTEGER (0..999)        OPTIONAL,   -- Need ON
    gnss-DataBitsSatList    GNSS-DataBitsSatList,
    ...
}

GNSS-DataBitsSatList ::= SEQUENCE (SIZE(1..64))OF GNSS-DataBitsSatElement

GNSS-DataBitsSatElement ::= SEQUENCE {
    svID                    SV-ID,
    gnss-DataBitsSgnList    GNSS-DataBitsSgnList,
    ...
}

GNSS-DataBitsSgnList ::= SEQUENCE (SIZE(1..8)) OF GNSS-DataBitsSgnElement

GNSS-DataBitsSgnElement ::= SEQUENCE {
    gnss-SignalType         GNSS-SignalID,
    gnss-DataBits           BIT STRING (SIZE (1..1024)),
    ...
}

-- ASN1STOP
-- ASN1START

GNSS-AcquisitionAssistance ::= SEQUENCE {
    gnss-SignalID               GNSS-SignalID,
    gnss-AcquisitionAssistList  GNSS-AcquisitionAssistList,
    ...,
    confidence-r10              INTEGER (0..100)    OPTIONAL    -- Need ON
}

GNSS-AcquisitionAssistList ::= SEQUENCE (SIZE(1..64)) OF GNSS-AcquisitionAssistElement

GNSS-AcquisitionAssistElement  ::= SEQUENCE {
    svID                        SV-ID,
    doppler0                    INTEGER (-2048..2047),
    doppler1                    INTEGER (0..63),
    dopplerUncertainty          INTEGER (0..4),
    codePhase                   INTEGER (0..1022),
    intCodePhase                INTEGER (0..127),
    codePhaseSearchWindow       INTEGER (0..31),
    azimuth                     INTEGER (0..511),
    elevation                   INTEGER (0..127),
    ...,
    codePhase1023               BOOLEAN             OPTIONAL,   -- Need OP
    dopplerUncertaintyExt-r10   ENUMERATED {    d60,
                                                d80,
                                                d100,
                                                d120,
                                                noInformation, ... }    OPTIONAL    -- Need ON
}

-- ASN1STOP
-- ASN1START

GNSS-Almanac ::= SEQUENCE {
    weekNumber                  INTEGER (0..255)    OPTIONAL,   -- Need ON
    toa                         INTEGER (0..255)    OPTIONAL,   -- Need ON
    ioda                        INTEGER (0..3)      OPTIONAL,   -- Need ON
    completeAlmanacProvided     BOOLEAN,
    gnss-AlmanacList            GNSS-AlmanacList,
    ...,
      toa-ext-v1240           INTEGER (256..1023) OPTIONAL,   -- Need ON
        ioda-ext-v1240          INTEGER (4..15)     OPTIONAL    -- Need ON

}

GNSS-AlmanacList ::= SEQUENCE (SIZE(1..64)) OF GNSS-AlmanacElement

GNSS-AlmanacElement ::= CHOICE {
    keplerianAlmanacSet             AlmanacKeplerianSet,        -- Model-1
    keplerianNAV-Almanac            AlmanacNAV-KeplerianSet,    -- Model-2
    keplerianReducedAlmanac         AlmanacReducedKeplerianSet, -- Model-3
    keplerianMidiAlmanac            AlmanacMidiAlmanacSet,      -- Model-4
    keplerianGLONASS                AlmanacGLONASS-AlmanacSet,  -- Model-5
    ecef-SBAS-Almanac               AlmanacECEF-SBAS-AlmanacSet,-- Model-6
    ...,
    keplerianBDS-Almanac-r12        AlmanacBDS-AlmanacSet-r12   -- Model-7
}

-- ASN1STOP
-- ASN1START

AlmanacKeplerianSet ::= SEQUENCE {
    svID                    SV-ID,
    kepAlmanacE             INTEGER (0..2047),
    kepAlmanacDeltaI        INTEGER (-1024..1023),
    kepAlmanacOmegaDot      INTEGER (-1024..1023),
    kepSV-StatusINAV        BIT STRING (SIZE (4)),
    kepSV-StatusFNAV        BIT STRING (SIZE (2))           OPTIONAL,   -- Need ON
    kepAlmanacAPowerHalf    INTEGER (-4096..4095),
    kepAlmanacOmega0        INTEGER (-32768..32767),
    kepAlmanacW             INTEGER (-32768..32767),
    kepAlmanacM0            INTEGER (-32768..32767),
    kepAlmanacAF0           INTEGER (-32768..32767),
    kepAlmanacAF1           INTEGER (-4096..4095),
    ...
}

-- ASN1STOP
-- ASN1START

AlmanacNAV-KeplerianSet ::= SEQUENCE {
    svID                    SV-ID,
    navAlmE                 INTEGER (0..65535),
    navAlmDeltaI            INTEGER (-32768..32767),
    navAlmOMEGADOT          INTEGER (-32768..32767),
    navAlmSVHealth          INTEGER (0..255),
    navAlmSqrtA             INTEGER (0..16777215),
    navAlmOMEGAo            INTEGER (-8388608..8388607),
    navAlmOmega             INTEGER (-8388608..8388607),
    navAlmMo                INTEGER (-8388608..8388607),
    navAlmaf0               INTEGER (-1024..1023),
    navAlmaf1               INTEGER (-1024..1023),
    ...
}

-- ASN1STOP
-- ASN1START

AlmanacReducedKeplerianSet ::= SEQUENCE {
    svID                    SV-ID,
    redAlmDeltaA            INTEGER (-128..127),
    redAlmOmega0            INTEGER (-64..63),
    redAlmPhi0              INTEGER (-64..63),
    redAlmL1Health          BOOLEAN,
    redAlmL2Health          BOOLEAN,
    redAlmL5Health          BOOLEAN,
    ...
}

-- ASN1STOP
-- ASN1START

AlmanacMidiAlmanacSet ::= SEQUENCE {
    svID                    SV-ID,
    midiAlmE                INTEGER (0..2047),
    midiAlmDeltaI           INTEGER (-1024..1023),
    midiAlmOmegaDot         INTEGER (-1024..1023),
    midiAlmSqrtA            INTEGER (0..131071),
    midiAlmOmega0           INTEGER (-32768..32767),
    midiAlmOmega            INTEGER (-32768..32767),
    midiAlmMo               INTEGER (-32768..32767),
    midiAlmaf0              INTEGER (-1024..1023),
    midiAlmaf1              INTEGER (-512..511),
    midiAlmL1Health         BOOLEAN,
    midiAlmL2Health         BOOLEAN,
    midiAlmL5Health         BOOLEAN,
    ...
}

-- ASN1STOP
-- ASN1START

AlmanacGLONASS-AlmanacSet ::= SEQUENCE {
    gloAlm-NA               INTEGER (1..1461),
    gloAlmnA                INTEGER (1..24),
    gloAlmHA                INTEGER (0..31),
    gloAlmLambdaA           INTEGER (-1048576..1048575),
    gloAlmtlambdaA          INTEGER (0..2097151),
    gloAlmDeltaIa           INTEGER (-131072..131071),
    gloAlmDeltaTA           INTEGER (-2097152..2097151),
    gloAlmDeltaTdotA        INTEGER (-64..63),
    gloAlmEpsilonA          INTEGER (0..32767),
    gloAlmOmegaA            INTEGER (-32768..32767),
    gloAlmTauA              INTEGER (-512..511),
    gloAlmCA                INTEGER (0..1),
    gloAlmMA                BIT STRING (SIZE(2))            OPTIONAL,   -- Need ON
    ...
}

-- ASN1STOP
-- ASN1START

AlmanacECEF-SBAS-AlmanacSet ::= SEQUENCE {
    sbasAlmDataID           INTEGER (0..3),
    svID                    SV-ID,
    sbasAlmHealth           BIT STRING (SIZE(8)),
    sbasAlmXg               INTEGER (-16384..16383),
    sbasAlmYg               INTEGER (-16384..16383),
    sbasAlmZg               INTEGER (-256..255),
    sbasAlmXgdot            INTEGER (-4..3),
    sbasAlmYgDot            INTEGER (-4..3),
    sbasAlmZgDot            INTEGER (-8..7),
    sbasAlmTo               INTEGER (0..2047),
    ...
}

-- ASN1STOP
-- ASN1START

AlmanacBDS-AlmanacSet-r12 ::= SEQUENCE {
    svID                    SV-ID,
    bdsAlmToa-r12           INTEGER (0..255)                    OPTIONAL,   -- Cond NotSameForAllSV
    bdsAlmSqrtA-r12         INTEGER (0..16777215),
    bdsAlmE-r12             INTEGER (0..131071),
    bdsAlmW-r12             INTEGER (-8388608..8388607),
    bdsAlmM0-r12            INTEGER (-8388608..8388607),
    bdsAlmOmega0-r12        INTEGER (-8388608..8388607),
    bdsAlmOmegaDot-r12      INTEGER (-65536..65535),
    bdsAlmDeltaI-r12        INTEGER (-32768..32767),
    bdsAlmA0-r12            INTEGER (-1024..1023),
    bdsAlmA1-r12            INTEGER (-1024..1023),
    bdsSvHealth-r12         BIT STRING (SIZE(9))                OPTIONAL,   -- Cond SV-ID
    ...
}

-- ASN1STOP
-- ASN1START

GNSS-UTC-Model ::= CHOICE {
    utcModel1           UTC-ModelSet1,          -- Model-1
    utcModel2           UTC-ModelSet2,          -- Model-2
    utcModel3           UTC-ModelSet3,          -- Model-3
    utcModel4           UTC-ModelSet4,          -- Model-4
    ...,
    utcModel5-r12       UTC-ModelSet5-r12       -- Model-5
}

-- ASN1STOP
-- ASN1START

UTC-ModelSet1 ::= SEQUENCE {
    gnss-Utc-A1         INTEGER (-8388608..8388607),
    gnss-Utc-A0         INTEGER (-2147483648..2147483647),
    gnss-Utc-Tot        INTEGER (0..255),
    gnss-Utc-WNt        INTEGER (0..255),
    gnss-Utc-DeltaTls   INTEGER (-128..127),
    gnss-Utc-WNlsf      INTEGER (0..255),
    gnss-Utc-DN         INTEGER (-128..127),
    gnss-Utc-DeltaTlsf  INTEGER (-128..127),
    ...
}

-- ASN1STOP
-- ASN1START

UTC-ModelSet2 ::= SEQUENCE {
    utcA0               INTEGER (-32768..32767),
    utcA1               INTEGER (-4096..4095),
    utcA2               INTEGER (-64..63),
    utcDeltaTls         INTEGER (-128..127),
    utcTot              INTEGER (0..65535),
    utcWNot             INTEGER (0..8191),
    utcWNlsf            INTEGER (0..255),
    utcDN               BIT STRING (SIZE(4)),
    utcDeltaTlsf        INTEGER (-128..127),
    ...
}

-- ASN1STOP
-- ASN1START

UTC-ModelSet3 ::= SEQUENCE {
    nA                  INTEGER (1..1461),
    tauC                INTEGER (-2147483648..2147483647),
    b1                  INTEGER (-1024..1023)                   OPTIONAL,   -- Cond GLONASS-M
    b2                  INTEGER (-512..511)                     OPTIONAL,   -- Cond GLONASS-M
    kp                  BIT STRING (SIZE(2))                    OPTIONAL,   -- Cond GLONASS-M
    ...
}

-- ASN1STOP
-- ASN1START

UTC-ModelSet4 ::= SEQUENCE {
    utcA1wnt            INTEGER (-8388608..8388607),
    utcA0wnt            INTEGER (-2147483648..2147483647),
    utcTot              INTEGER (0..255),
    utcWNt              INTEGER (0..255),
    utcDeltaTls         INTEGER (-128..127),
    utcWNlsf            INTEGER (0..255),
    utcDN               INTEGER (-128..127),
    utcDeltaTlsf        INTEGER (-128..127),
    utcStandardID       INTEGER (0..7),
    ...
}

-- ASN1STOP
-- ASN1START

UTC-ModelSet5-r12 ::= SEQUENCE {
    utcA0-r12           INTEGER (-2147483648..2147483647),
    utcA1-r12           INTEGER (-8388608..8388607),
    utcDeltaTls-r12     INTEGER (-128..127),
    utcWNlsf-r12        INTEGER (0..255),
    utcDN-r12           INTEGER (0..255),
    utcDeltaTlsf-r12    INTEGER (-128..127),
    ...
}

-- ASN1STOP
-- ASN1START

GNSS-AuxiliaryInformation ::= CHOICE {
    gnss-ID-GPS     GNSS-ID-GPS,
    gnss-ID-GLONASS GNSS-ID-GLONASS,
    ...
}

GNSS-ID-GPS ::= SEQUENCE    (SIZE(1..64)) OF GNSS-ID-GPS-SatElement

GNSS-ID-GPS-SatElement ::= SEQUENCE {
    svID                SV-ID,
    signalsAvailable    GNSS-SignalIDs,
    ...
}

GNSS-ID-GLONASS ::= SEQUENCE (SIZE(1..64)) OF GNSS-ID-GLONASS-SatElement

GNSS-ID-GLONASS-SatElement ::= SEQUENCE {
    svID                SV-ID,
    signalsAvailable    GNSS-SignalIDs,
    channelNumber       INTEGER (-7..13)        OPTIONAL,       -- Cond FDMA
    ...
}

-- ASN1STOP
-- ASN1START

BDS-DifferentialCorrections-r12 ::= SEQUENCE {
    dbds-RefTime-r12            INTEGER (0..3599),
    bds-SgnTypeList-r12         BDS-SgnTypeList-r12,
    ...
}

BDS-SgnTypeList-r12 ::= SEQUENCE (SIZE (1..3)) OF BDS-SgnTypeElement-r12

BDS-SgnTypeElement-r12 ::= SEQUENCE {
    gnss-SignalID               GNSS-SignalID               OPTIONAL,   -- Need ON
    dbds-CorrectionList-r12     DBDS-CorrectionList-r12,
    ...
}

DBDS-CorrectionList-r12 ::= SEQUENCE (SIZE (1..64)) OF DBDS-CorrectionElement-r12

DBDS-CorrectionElement-r12 ::= SEQUENCE {
    svID                        SV-ID,
    bds-UDREI-r12               INTEGER (0..15),
    bds-RURAI-r12               INTEGER (0..15),
    bds-ECC-DeltaT-r12          INTEGER (-4096..4095),
    ...
}

-- ASN1STOP
-- ASN1START

BDS-GridModelParameter-r12 ::= SEQUENCE {
    bds-RefTime-r12         INTEGER (0..3599),
    gridIonList-r12         GridIonList-r12,
    ...
}

GridIonList-r12 ::= SEQUENCE (SIZE (1..320)) OF GridIonElement-r12

GridIonElement-r12 ::= SEQUENCE {
    igp-ID-r12              INTEGER (1..320),
    dt-r12                  INTEGER (0..511),
    givei-r12               INTEGER (0..15) ,
    ...
}

-- ASN1STOP
-- ASN1START

A-GNSS-RequestAssistanceData ::= SEQUENCE {
    gnss-CommonAssistDataReq        GNSS-CommonAssistDataReq        OPTIONAL, -- Cond CommonADReq
    gnss-GenericAssistDataReq       GNSS-GenericAssistDataReq       OPTIONAL, -- Cond GenADReq
    ...
}

-- ASN1STOP
-- ASN1START

GNSS-CommonAssistDataReq ::= SEQUENCE {
    gnss-ReferenceTimeReq               GNSS-ReferenceTimeReq
                                                                OPTIONAL, -- Cond RefTimeReq
    gnss-ReferenceLocationReq           GNSS-ReferenceLocationReq
                                                                OPTIONAL, -- Cond RefLocReq
    gnss-IonosphericModelReq            GNSS-IonosphericModelReq
                                                                OPTIONAL, -- Cond IonoModReq
    gnss-EarthOrientationParametersReq  GNSS-EarthOrientationParametersReq
                                                                OPTIONAL, -- Cond EOPReq
    ...
}

-- ASN1STOP
-- ASN1START

GNSS-GenericAssistDataReq ::= SEQUENCE (SIZE (1..16)) OF GNSS-GenericAssistDataReqElement

GNSS-GenericAssistDataReqElement ::= SEQUENCE {
    gnss-ID                         GNSS-ID,
    sbas-ID                         SBAS-ID                         OPTIONAL, -- Cond GNSS-ID-SBAS
    gnss-TimeModelsReq              GNSS-TimeModelListReq           OPTIONAL, -- Cond TimeModReq
    gnss-DifferentialCorrectionsReq GNSS-DifferentialCorrectionsReq OPTIONAL, -- Cond DGNSS-Req
    gnss-NavigationModelReq         GNSS-NavigationModelReq         OPTIONAL, -- Cond NavModReq
    gnss-RealTimeIntegrityReq       GNSS-RealTimeIntegrityReq       OPTIONAL, -- Cond RTIReq
    gnss-DataBitAssistanceReq       GNSS-DataBitAssistanceReq       OPTIONAL, -- Cond DataBitsReq
    gnss-AcquisitionAssistanceReq   GNSS-AcquisitionAssistanceReq   OPTIONAL, -- Cond AcquAssistReq
    gnss-AlmanacReq                 GNSS-AlmanacReq                 OPTIONAL, -- Cond AlmanacReq
    gnss-UTCModelReq                GNSS-UTC-ModelReq               OPTIONAL, -- Cond UTCModReq
    gnss-AuxiliaryInformationReq    GNSS-AuxiliaryInformationReq    OPTIONAL, -- Cond AuxInfoReq
    ...,

        bds-DifferentialCorrectionsReq-r12
                                    BDS-DifferentialCorrectionsReq-r12
                                                                    OPTIONAL,   -- Cond DBDS-Req
        bds-GridModelReq-r12        BDS-GridModelReq-r12            OPTIONAL    -- Cond BDS-GridModReq

}

-- ASN1STOP
-- ASN1START

GNSS-ReferenceTimeReq ::= SEQUENCE {
    gnss-TimeReqPrefList    SEQUENCE (SIZE (1..8)) OF GNSS-ID,
    gps-TOW-assistReq       BOOLEAN                             OPTIONAL, -- Cond gps
    notOfLeapSecReq         BOOLEAN                             OPTIONAL, -- Cond glonass
    ...
}

-- ASN1STOP
-- ASN1START

GNSS-ReferenceLocationReq ::=   SEQUENCE {
    ...
}

-- ASN1STOP
-- ASN1START

GNSS-IonosphericModelReq ::=    SEQUENCE {
    klobucharModelReq       BIT STRING (SIZE(2))    OPTIONAL,   -- Cond klobuchar
    neQuickModelReq         NULL                    OPTIONAL,   -- Cond nequick
    ...
}

-- ASN1STOP
-- ASN1START

GNSS-EarthOrientationParametersReq ::=  SEQUENCE {
    ...
}

-- ASN1STOP
-- ASN1START

GNSS-TimeModelListReq ::= SEQUENCE (SIZE(1..15)) OF GNSS-TimeModelElementReq

GNSS-TimeModelElementReq ::= SEQUENCE {
    gnss-TO-IDsReq  INTEGER (1..15),
    deltaTreq       BOOLEAN,
    ...
}

-- ASN1STOP
-- ASN1START

GNSS-DifferentialCorrectionsReq ::=     SEQUENCE {
    dgnss-SignalsReq            GNSS-SignalIDs,
    dgnss-ValidityTimeReq       BOOLEAN,
    ...
}

-- ASN1STOP
-- ASN1START

GNSS-NavigationModelReq ::=     CHOICE {
    storedNavList       StoredNavListInfo,
    reqNavList          ReqNavListInfo,
    ...
}


StoredNavListInfo ::= SEQUENCE {
    gnss-WeekOrDay          INTEGER (0..4095),
    gnss-Toe                INTEGER (0..255),
    t-toeLimit              INTEGER (0..15),
    satListRelatedDataList  SatListRelatedDataList  OPTIONAL,
    ...
}

SatListRelatedDataList ::= SEQUENCE (SIZE (1..64)) OF SatListRelatedDataElement

SatListRelatedDataElement ::= SEQUENCE {
    svID                SV-ID,
    iod                 BIT STRING (SIZE(11)),
    clockModelID        INTEGER (1..8)          OPTIONAL,
orbitModelID        INTEGER (1..8)          OPTIONAL,
    ...
}

ReqNavListInfo ::=  SEQUENCE {
    svReqList               BIT STRING (SIZE (64)),
    clockModelID-PrefList   SEQUENCE (SIZE (1..8)) OF   INTEGER (1..8)      OPTIONAL,
    orbitModelID-PrefList   SEQUENCE (SIZE (1..8)) OF   INTEGER (1..8)      OPTIONAL,
    addNavparamReq          BOOLEAN             OPTIONAL,   -- Cond orbitModelID-2
    ...
}


-- ASN1STOP
-- ASN1START

GNSS-RealTimeIntegrityReq ::=   SEQUENCE {
    ...
}

-- ASN1STOP
-- ASN1START

GNSS-DataBitAssistanceReq ::=   SEQUENCE {
    gnss-TOD-Req        INTEGER (0..3599),
    gnss-TOD-FracReq    INTEGER (0..999)        OPTIONAL,
    dataBitInterval     INTEGER (0..15),
    gnss-SignalType     GNSS-SignalIDs,
    gnss-DataBitsReq    GNSS-DataBitsReqSatList OPTIONAL,
    ...
}

GNSS-DataBitsReqSatList ::= SEQUENCE (SIZE(1..64)) OF GNSS-DataBitsReqSatElement

GNSS-DataBitsReqSatElement ::= SEQUENCE {
    svID                SV-ID,
    ...
}

-- ASN1STOP
-- ASN1START

GNSS-AcquisitionAssistanceReq ::=   SEQUENCE {
    gnss-SignalID-Req       GNSS-SignalID,
    ...
}

-- ASN1STOP
-- ASN1START

GNSS-AlmanacReq ::= SEQUENCE {
    modelID             INTEGER(1..8)   OPTIONAL,
    ...
}

-- ASN1STOP
-- ASN1START

GNSS-UTC-ModelReq ::=   SEQUENCE {
    modelID             INTEGER(1..8)   OPTIONAL,
    ...
}

-- ASN1STOP
-- ASN1START

GNSS-AuxiliaryInformationReq ::=    SEQUENCE {
    ...
}

-- ASN1STOP
-- ASN1START

BDS-DifferentialCorrectionsReq-r12 ::=  SEQUENCE {
    dgnss-SignalsReq            GNSS-SignalIDs,
    ...
}

-- ASN1STOP
-- ASN1START

BDS-GridModelReq-r12 ::=    SEQUENCE {
    ...
}

-- ASN1STOP
-- ASN1START

A-GNSS-ProvideLocationInformation ::= SEQUENCE {
    gnss-SignalMeasurementInformation   GNSS-SignalMeasurementInformation       OPTIONAL,
    gnss-LocationInformation            GNSS-LocationInformation                OPTIONAL,
    gnss-Error                          A-GNSS-Error                            OPTIONAL,
    ...
}

-- ASN1STOP
-- ASN1START

GNSS-SignalMeasurementInformation ::= SEQUENCE {
    measurementReferenceTime        MeasurementReferenceTime,
    gnss-MeasurementList            GNSS-MeasurementList,
    ...
}

-- ASN1STOP
-- ASN1START

MeasurementReferenceTime  ::= SEQUENCE {
    gnss-TOD-msec       INTEGER (0..3599999),
    gnss-TOD-frac       INTEGER (0..3999)           OPTIONAL,
    gnss-TOD-unc        INTEGER (0..127)            OPTIONAL,
    gnss-TimeID         GNSS-ID,
    networkTime         CHOICE {
        eUTRA   SEQUENCE {
                physCellId          INTEGER (0..503),
                cellGlobalId        CellGlobalIdEUTRA-AndUTRA       OPTIONAL,
                systemFrameNumber   BIT STRING (SIZE (10)),
                ...
                },
        uTRA    SEQUENCE {
                mode                    CHOICE {
                                        fdd         SEQUENCE {
                                                    primary-CPICH-Info  INTEGER (0..511),
                                                    ...
                                                    },
                                        tdd         SEQUENCE {
                                                    cellParameters      INTEGER (0..127),
                                                    ...
                                                    }
                                        },
                cellGlobalId            CellGlobalIdEUTRA-AndUTRA       OPTIONAL,
                referenceSystemFrameNumber
                                        INTEGER (0..4095),
                ...
                },
        gSM     SEQUENCE {
                bcchCarrier         INTEGER (0..1023),
                bsic                INTEGER (0..63),
                cellGlobalId        CellGlobalIdGERAN                   OPTIONAL,
                referenceFrame      SEQUENCE {
                                    referenceFN         INTEGER (0..65535),
                                    referenceFNMSB      INTEGER (0..63)     OPTIONAL,
                                    ...
                                    },
                deltaGNSS-TOD       INTEGER (0 .. 127)      OPTIONAL,
                ...
                },
        ...,
        nbIoT-r14
                SEQUENCE {
                nbPhysCellId-r14    INTEGER (0..503),
                nbCellGlobalId-r14  ECGI                        OPTIONAL,
                sfn-r14             BIT STRING (SIZE (10)),
                hyperSFN-r14        BIT STRING (SIZE (10))      OPTIONAL,
                ...
                }
        }       OPTIONAL,
    ...
}

-- ASN1STOP
-- ASN1START

GNSS-MeasurementList  ::= SEQUENCE (SIZE(1..16)) OF GNSS-MeasurementForOneGNSS

GNSS-MeasurementForOneGNSS ::= SEQUENCE {
    gnss-ID                 GNSS-ID,
    gnss-SgnMeasList        GNSS-SgnMeasList,
    ...
}

GNSS-SgnMeasList ::= SEQUENCE (SIZE(1..8)) OF GNSS-SgnMeasElement

GNSS-SgnMeasElement ::= SEQUENCE {
    gnss-SignalID           GNSS-SignalID,
    gnss-CodePhaseAmbiguity INTEGER (0..127)        OPTIONAL,
    gnss-SatMeasList        GNSS-SatMeasList,
    ...
}

GNSS-SatMeasList ::= SEQUENCE (SIZE(1..64)) OF GNSS-SatMeasElement

GNSS-SatMeasElement ::= SEQUENCE {
    svID                SV-ID,
    cNo                 INTEGER (0..63),
    mpathDet            ENUMERATED {notMeasured (0), low (1), medium (2), high (3), ...},
    carrierQualityInd   INTEGER (0..3)              OPTIONAL,
    codePhase           INTEGER (0..2097151),
    integerCodePhase    INTEGER (0..127)            OPTIONAL,
    codePhaseRMSError   INTEGER (0..63),
    doppler             INTEGER (-32768..32767)     OPTIONAL,
    adr                 INTEGER (0..33554431)       OPTIONAL,
    ...
}

-- ASN1STOP
-- ASN1START

GNSS-LocationInformation ::= SEQUENCE {
    measurementReferenceTime        MeasurementReferenceTime,
    agnss-List                      GNSS-ID-Bitmap,
    ...
}

-- ASN1STOP
-- ASN1START

A-GNSS-RequestLocationInformation ::= SEQUENCE {
    gnss-PositioningInstructions        GNSS-PositioningInstructions,
    ...
}

-- ASN1STOP
-- ASN1START

GNSS-PositioningInstructions ::= SEQUENCE {
    gnss-Methods                GNSS-ID-Bitmap,
    fineTimeAssistanceMeasReq   BOOLEAN,
    adrMeasReq                  BOOLEAN,
    multiFreqMeasReq            BOOLEAN,
    assistanceAvailability      BOOLEAN,
    ...
}

-- ASN1STOP
-- ASN1START

A-GNSS-ProvideCapabilities ::= SEQUENCE {
    gnss-SupportList            GNSS-SupportList                OPTIONAL,
    assistanceDataSupportList   AssistanceDataSupportList       OPTIONAL,
    locationCoordinateTypes     LocationCoordinateTypes         OPTIONAL,
    velocityTypes               VelocityTypes                   OPTIONAL,
    ...,
     periodicalReportingNotSupported-r14
                                PositioningModes                OPTIONAL,
        idleStateForMeasurements-r14
                                ENUMERATED { required }         OPTIONAL

}

GNSS-SupportList ::= SEQUENCE (SIZE(1..16)) OF GNSS-SupportElement

GNSS-SupportElement ::= SEQUENCE {
    gnss-ID                         GNSS-ID,
    sbas-IDs                        SBAS-IDs                    OPTIONAL,   -- Cond GNSS-ID-SBAS
    agnss-Modes                     PositioningModes,
    gnss-Signals                    GNSS-SignalIDs,
    fta-MeasSupport                 SEQUENCE {
                                        cellTime    AccessTypes,
                                        mode        PositioningModes,
                                        ...
                                    }                           OPTIONAL,   -- Cond fta
    adr-Support                     BOOLEAN,
    velocityMeasurementSupport      BOOLEAN,
    ...
}

AssistanceDataSupportList ::= SEQUENCE {
    gnss-CommonAssistanceDataSupport    GNSS-CommonAssistanceDataSupport,
    gnss-GenericAssistanceDataSupport   GNSS-GenericAssistanceDataSupport,
    ...
}


-- ASN1STOP
-- ASN1START

GNSS-CommonAssistanceDataSupport ::= SEQUENCE {
    gnss-ReferenceTimeSupport               GNSS-ReferenceTimeSupport
                                                                OPTIONAL, -- Cond RefTimeSup
    gnss-ReferenceLocationSupport           GNSS-ReferenceLocationSupport
                                                                OPTIONAL, -- Cond RefLocSup
    gnss-IonosphericModelSupport            GNSS-IonosphericModelSupport
                                                                OPTIONAL, -- Cond IonoModSup
    gnss-EarthOrientationParametersSupport  GNSS-EarthOrientationParametersSupport
                                                                OPTIONAL, -- Cond EOPSup
    ...
}

-- ASN1STOP
-- ASN1START

GNSS-ReferenceTimeSupport ::=   SEQUENCE {
    gnss-SystemTime     GNSS-ID-Bitmap,
    fta-Support         AccessTypes                                     OPTIONAL, -- Cond fta
    ...
}

-- ASN1STOP
-- ASN1START

GNSS-ReferenceLocationSupport ::=   SEQUENCE {
    ...
}

-- ASN1STOP
-- ASN1START

GNSS-IonosphericModelSupport ::=    SEQUENCE {
    ionoModel       BIT STRING {    klobuchar   (0),
                                    neQuick     (1) } (SIZE (1..8)),
    ...
}

-- ASN1STOP
-- ASN1START

GNSS-EarthOrientationParametersSupport ::=  SEQUENCE {
    ...
}

-- ASN1STOP
-- ASN1START

GNSS-GenericAssistanceDataSupport ::=
                                SEQUENCE (SIZE (1..16)) OF GNSS-GenericAssistDataSupportElement

GNSS-GenericAssistDataSupportElement ::= SEQUENCE {
    gnss-ID                             GNSS-ID,
    sbas-ID                             SBAS-ID                     OPTIONAL, -- Cond GNSS‑ID‑SBAS
    gnss-TimeModelsSupport              GNSS-TimeModelListSupport
                                                                    OPTIONAL, -- Cond TimeModSup
    gnss-DifferentialCorrectionsSupport GNSS-DifferentialCorrectionsSupport
                                                                    OPTIONAL, -- Cond DGNSS-Sup
    gnss-NavigationModelSupport         GNSS-NavigationModelSupport
                                                                    OPTIONAL, -- Cond NavModSup
    gnss-RealTimeIntegritySupport       GNSS-RealTimeIntegritySupport
                                                                    OPTIONAL, -- Cond RTISup
    gnss-DataBitAssistanceSupport       GNSS-DataBitAssistanceSupport
                                                                    OPTIONAL, -- Cond DataBitsSup
    gnss-AcquisitionAssistanceSupport   GNSS-AcquisitionAssistanceSupport
                                                                    OPTIONAL, -- Cond AcquAssistSup
    gnss-AlmanacSupport                 GNSS-AlmanacSupport
                                                                    OPTIONAL, -- Cond AlmanacSup
    gnss-UTC-ModelSupport               GNSS-UTC-ModelSupport
                                                                    OPTIONAL, -- Cond UTCModSup
    gnss-AuxiliaryInformationSupport    GNSS-AuxiliaryInformationSupport
                                                                    OPTIONAL, -- Cond AuxInfoSup
    ...,

        bds-DifferentialCorrectionsSupport-r12
                                        BDS-DifferentialCorrectionsSupport-r12
                                                                    OPTIONAL, -- Cond DBDS-Sup
        bds-GridModelSupport-r12        BDS-GridModelSupport-r12
                                                                    OPTIONAL     -- Cond BDS-GridModSup

}

-- ASN1STOP
-- ASN1START

GNSS-TimeModelListSupport ::=   SEQUENCE {
    ...
}

-- ASN1STOP
-- ASN1START

GNSS-DifferentialCorrectionsSupport ::=     SEQUENCE {
    gnssSignalIDs           GNSS-SignalIDs,
    dgnss-ValidityTimeSup   BOOLEAN,
    ...
}

-- ASN1STOP
-- ASN1START

GNSS-NavigationModelSupport ::= SEQUENCE {
    clockModel      BIT STRING {    model-1     (0),
                                    model-2     (1),
                                    model-3     (2),
                                    model-4     (3),
                                    model-5     (4),
                                    model-6     (5) } (SIZE (1..8))     OPTIONAL,
    orbitModel      BIT STRING {    model-1     (0),
                                    model-2     (1),
                                    model-3     (2),
                                    model-4     (3),
                                    model-5     (4),
                                    model-6     (5) } (SIZE (1..8))     OPTIONAL,
    ...
}

-- ASN1STOP
-- ASN1START

GNSS-RealTimeIntegritySupport ::=   SEQUENCE {
    ...
}

-- ASN1STOP
-- ASN1START

GNSS-DataBitAssistanceSupport ::=   SEQUENCE {
    ...
}

-- ASN1STOP
-- ASN1START

GNSS-AcquisitionAssistanceSupport ::=   SEQUENCE {
    ...,
    confidenceSupport-r10                   ENUMERATED { true }     OPTIONAL,
    dopplerUncertaintyExtSupport-r10        ENUMERATED { true }     OPTIONAL
}

-- ASN1STOP
-- ASN1START

GNSS-AlmanacSupport ::=     SEQUENCE {
    almanacModel        BIT STRING {    model-1     (0),
                                        model-2     (1),
                                        model-3     (2),
                                        model-4     (3),
                                        model-5     (4),
                                        model-6     (5),
                                        model-7     (6) } (SIZE (1..8))     OPTIONAL,
    ...
}

-- ASN1STOP
-- ASN1START

GNSS-UTC-ModelSupport ::=   SEQUENCE {
    utc-Model       BIT STRING {    model-1     (0),
                                    model-2     (1),
                                    model-3     (2),
                                    model-4     (3),
                                    model-5     (4) } (SIZE (1..8))     OPTIONAL,
    ...
}

-- ASN1STOP
-- ASN1START

GNSS-AuxiliaryInformationSupport ::=    SEQUENCE {
    ...
}

-- ASN1STOP
-- ASN1START

BDS-DifferentialCorrectionsSupport-r12 ::=  SEQUENCE {
    gnssSignalIDs           GNSS-SignalIDs,
    ...
}

-- ASN1STOP
-- ASN1START

BDS-GridModelSupport-r12 ::=    SEQUENCE {
    ...
}

-- ASN1STOP
-- ASN1START

A-GNSS-RequestCapabilities ::= SEQUENCE {
    gnss-SupportListReq             BOOLEAN,
    assistanceDataSupportListReq    BOOLEAN,
    locationVelocityTypesReq        BOOLEAN,
    ...
}

-- ASN1STOP
-- ASN1START

A-GNSS-Error ::= CHOICE {
    locationServerErrorCauses       GNSS-LocationServerErrorCauses,
    targetDeviceErrorCauses         GNSS-TargetDeviceErrorCauses,
    ...
}

-- ASN1STOP
-- ASN1START

GNSS-LocationServerErrorCauses ::= SEQUENCE {
    cause       ENUMERATED  {
                    undefined,
                    undeliveredAssistanceDataIsNotSupportedByServer,
                    undeliveredAssistanceDataIsSupportedButCurrentlyNotAvailableByServer,                               undeliveredAssistanceDataIsPartlyNotSupportedAndPartlyNotAvailableByServer,
                    ...
                    },
    ...
}

-- ASN1STOP
-- ASN1START

GNSS-TargetDeviceErrorCauses ::= SEQUENCE {
    cause       ENUMERATED {    undefined,
                                thereWereNotEnoughSatellitesReceived,
                                assistanceDataMissing,
                                notAllRequestedMeasurementsPossible,
                                ...
                            },
    fineTimeAssistanceMeasurementsNotPossible       NULL        OPTIONAL,
    adrMeasurementsNotPossible                      NULL        OPTIONAL,
    multiFrequencyMeasurementsNotPossible           NULL        OPTIONAL,
    ...
}

-- ASN1STOP
-- ASN1START

GNSS-ID ::= SEQUENCE {
    gnss-id             ENUMERATED{ gps, sbas, qzss, galileo, glonass, ..., bds },
    ...
}

-- ASN1STOP
-- ASN1START

GNSS-ID-Bitmap ::= SEQUENCE {
    gnss-ids            BIT STRING {    gps         (0),
                                        sbas        (1),
                                        qzss        (2),
                                        galileo     (3),
                                        glonass     (4),
                                        bds         (5) } (SIZE (1..16)),
    ...
}

-- ASN1STOP
-- ASN1START

GNSS-SignalID   ::= SEQUENCE {
    gnss-SignalID       INTEGER (0 .. 7),
    ...
}

-- ASN1STOP
-- ASN1START

GNSS-SignalIDs  ::= SEQUENCE {
    gnss-SignalIDs      BIT STRING (SIZE(8)),
    ...
}

-- ASN1STOP
-- ASN1START

SBAS-ID ::= SEQUENCE {
    sbas-id             ENUMERATED { waas, egnos, msas, gagan, ...},
    ...
}

-- ASN1STOP
-- ASN1START

SBAS-IDs ::= SEQUENCE {
    sbas-IDs        BIT STRING {    waas        (0),
                                    egnos       (1),
                                    msas        (2),
                                    gagan       (3)  } (SIZE (1..8)),
    ...
}

-- ASN1STOP
-- ASN1START

SV-ID ::= SEQUENCE {
    satellite-id        INTEGER(0..63),
    ...
}

-- ASN1STOP
-- ASN1START

ECID-ProvideLocationInformation ::= SEQUENCE {
    ecid-SignalMeasurementInformation   ECID-SignalMeasurementInformation       OPTIONAL,
    ecid-Error                          ECID-Error                              OPTIONAL,
    ...
}

-- ASN1STOP
-- ASN1START

ECID-SignalMeasurementInformation ::= SEQUENCE {
    primaryCellMeasuredResults  MeasuredResultsElement  OPTIONAL,
    measuredResultsList         MeasuredResultsList,
    ...
}

MeasuredResultsList ::= SEQUENCE (SIZE(1..32)) OF MeasuredResultsElement

MeasuredResultsElement ::= SEQUENCE {
    physCellId      INTEGER (0..503),
    cellGlobalId    CellGlobalIdEUTRA-AndUTRA           OPTIONAL,
    arfcnEUTRA      ARFCN-ValueEUTRA,
    systemFrameNumber
                    BIT STRING (SIZE (10))              OPTIONAL,
    rsrp-Result     INTEGER (0..97)                     OPTIONAL,
    rsrq-Result     INTEGER (0..34)                     OPTIONAL,
    ue-RxTxTimeDiff INTEGER (0..4095)                   OPTIONAL,
    ...,
     arfcnEUTRA-v9a0      ARFCN-ValueEUTRA-v9a0       OPTIONAL        -- Cond EARFCN-max
    ,
     nrsrp-Result-r14     INTEGER (0..113)            OPTIONAL,
       nrsrq-Result-r14     INTEGER (0..74)             OPTIONAL,
       carrierFreqOffsetNB-r14
                            CarrierFreqOffsetNB-r14     OPTIONAL,       -- Cond NB-IoT
       hyperSFN-r14         BIT STRING (SIZE (10))      OPTIONAL

}

-- ASN1STOP
-- ASN1START

ECID-RequestLocationInformation ::= SEQUENCE {
    requestedMeasurements       BIT STRING {    rsrpReq     (0),
                                                rsrqReq     (1),
                                                ueRxTxReq   (2),
                                                nrsrpReq-r14    (3),
                                                nrsrqReq-r14    (4)} (SIZE(1..8)),
    ...
}

-- ASN1STOP
-- ASN1START

ECID-ProvideCapabilities ::= SEQUENCE {
    ecid-MeasSupported  BIT STRING {    rsrpSup     (0),
                                        rsrqSup     (1),
                                        ueRxTxSup   (2),
                                        nrsrpSup-r14    (3),
                                        nrsrqSup-r14    (4)} (SIZE(1..8)),
    ...,
      ueRxTxSupTDD-r13                    ENUMERATED { true }             OPTIONAL
    ,
      periodicalReporting-r14             ENUMERATED { supported }        OPTIONAL,
        triggeredReporting-r14              ENUMERATED { supported }        OPTIONAL,
        idleStateForMeasurements-r14        ENUMERATED { required }         OPTIONAL

}

-- ASN1STOP
-- ASN1START

ECID-RequestCapabilities ::= SEQUENCE {
    ...
}

-- ASN1STOP
-- ASN1START

ECID-Error ::= CHOICE {
    locationServerErrorCauses       ECID-LocationServerErrorCauses,
    targetDeviceErrorCauses         ECID-TargetDeviceErrorCauses,
    ...
}

-- ASN1STOP
-- ASN1START

ECID-LocationServerErrorCauses ::= SEQUENCE {
    cause       ENUMERATED  {   undefined,
                                ...
                            },
    ...
}

-- ASN1STOP
-- ASN1START

ECID-TargetDeviceErrorCauses ::= SEQUENCE {
    cause       ENUMERATED {    undefined,
                                requestedMeasurementNotAvailable,
                                notAllrequestedMeasurementsPossible,
                                ...
                            },
    rsrpMeasurementNotPossible              NULL        OPTIONAL,
    rsrqMeasurementNotPossible              NULL        OPTIONAL,
    ueRxTxMeasurementNotPossible            NULL        OPTIONAL,
    ...,

      nrsrpMeasurementNotPossible-r14       NULL        OPTIONAL,
      nrsrqMeasurementNotPossible-r14       NULL        OPTIONAL

}

-- ASN1STOP
-- ASN1START

TBS-ProvideLocationInformation-r13 ::= SEQUENCE {
    tbs-MeasurementInformation-r13          TBS-MeasurementInformation-r13      OPTIONAL,
    tbs-Error-r13                           TBS-Error-r13                       OPTIONAL,
    ...
}

-- ASN1STOP
-- ASN1START

TBS-MeasurementInformation-r13 ::= SEQUENCE {
    measurementReferenceTime-r13    UTCTime                     OPTIONAL,
    mbs-SgnMeasList-r13             MBS-BeaconMeasList-r13      OPTIONAL,   -- Cond MBS
    ...
}

-- ASN1STOP
-- ASN1START

MBS-BeaconMeasList-r13 ::= SEQUENCE (SIZE(1..64)) OF MBS-BeaconMeasElement-r13

MBS-BeaconMeasElement-r13 ::= SEQUENCE {
    transmitterID-r13               INTEGER (0..32767),
    codePhase-r13                   INTEGER (0..2097151),
    codePhaseRMSError-r13           INTEGER (0..63),
    ...,
     rssi-r14                     INTEGER (-130..-30)     OPTIONAL

}

-- ASN1STOP
-- ASN1START

TBS-RequestLocationInformation-r13 ::= SEQUENCE {
    mbsSgnMeasListReq-r13               BOOLEAN,
    ...,
      mbsAssistanceAvailability-r14   BOOLEAN                         OPTIONAL,   -- Need ON
        mbsRequestedMeasurements-r14    BIT STRING {
                                        rssi        (0)} (SIZE(1..8))   OPTIONAL    -- Need ON

}

-- ASN1STOP
-- ASN1START

TBS-ProvideCapabilities-r13 ::= SEQUENCE {
    tbs-Modes-r13           BIT STRING {    standalone      (0),
                                            ue-assisted     (1),
                                            ue-based        (2)} (SIZE (1..8)),
    ...,
      mbs-AssistanceDataSupportList-r14   MBS-AssistanceDataSupportList-r14       OPTIONAL,
        periodicalReportingSupported-r14    PositioningModes                        OPTIONAL,
        mbs-ConfigSupport-r14   BIT STRING {    tb1     (0),
                                                tb2     (1),
                                                tb3     (2),
                                                tb4     (3)} (SIZE (1..8))          OPTIONAL,
        mbs-IdleStateForMeasurements-r14        ENUMERATED { required }             OPTIONAL

}

-- ASN1STOP
-- ASN1START

MBS-AssistanceDataSupportList-r14 ::= SEQUENCE {
    mbs-AcquisitionAssistanceDataSupport-r14    BOOLEAN,
    mbs-AlmanacAssistanceDataSupport-r14        BOOLEAN,
    ...
}

-- ASN1STOP
-- ASN1START

TBS-RequestCapabilities-r13 ::= SEQUENCE {
    ...
}

-- ASN1STOP
-- ASN1START

TBS-Error-r13 ::= CHOICE {
    locationServerErrorCauses-r13       TBS-LocationServerErrorCauses-r13,
    targetDeviceErrorCauses-r13         TBS-TargetDeviceErrorCauses-r13,
    ...
}

-- ASN1STOP
-- ASN1START

TBS-LocationServerErrorCauses-r13 ::= SEQUENCE {
    cause-r13       ENUMERATED  {   undefined,
                                    ...,
                                    assistanceDataNotSupportedByServer-v1420,
                                    assistanceDataSupportedButCurrentlyNotAvailableByServer-v1420
                                },
    ...
}

-- ASN1STOP
-- ASN1START

TBS-TargetDeviceErrorCauses-r13 ::= SEQUENCE {
    cause-r13       ENUMERATED {    undefined,
                                    thereWereNotEnoughMBSBeaconsReceived,
                                    ...,
                                    assistanceDataMissing-v1420
                                },
    ...
}

-- ASN1STOP
-- ASN1START

TBS-ProvideAssistanceData-r14 ::= SEQUENCE {
    tbs-AssistanceDataList-r14  TBS-AssistanceDataList-r14  OPTIONAL,   -- Need ON
    tbs-Error-r14               TBS-Error-r13               OPTIONAL,   -- Need ON
    ...
}

-- ASN1STOP
-- ASN1START

TBS-AssistanceDataList-r14 ::= SEQUENCE {
    mbs-AssistanceDataList-r14      MBS-AssistanceDataList-r14      OPTIONAL,   -- Need ON
    ...
}

MBS-AssistanceDataList-r14 ::= SEQUENCE (SIZE (1..maxMBS-r14)) OF MBS-AssistanceDataElement-r14

MBS-AssistanceDataElement-r14 ::= SEQUENCE {
    mbs-AlmanacAssistance-r14       MBS-AlmanacAssistance-r14           OPTIONAL,   -- Need ON
    mbs-AcquisitionAssistance-r14   MBS-AcquisitionAssistance-r14       OPTIONAL,   -- Need ON
    ...
}

maxMBS-r14      INTEGER ::= 64

-- ASN1STOP
-- ASN1START

MBS-AlmanacAssistance-r14 ::= SEQUENCE {
    transmitterID-r14           INTEGER (0..32767),
    transmitterLatitude-r14     BIT STRING (SIZE (26)),
    transmitterLongitude-r14    BIT STRING (SIZE (27)),
    transmitterAltitude-r14     BIT STRING (SIZE (15)),
    timeCorrection-r14          INTEGER (0..25)     OPTIONAL,   -- Need ON
    ...
}

-- ASN1STOP
-- ASN1START

MBS-AcquisitionAssistance-r14 ::= SEQUENCE {
    transmitterID-r14               INTEGER (0..32767)                      OPTIONAL,   -- Need ON
    mbsConfiguration-r14            ENUMERATED {tb1, tb2, tb3, tb4, ...}    OPTIONAL,   -- Need ON
    pnCodeIndex-r14                 INTEGER (1..128)                        OPTIONAL,   -- Need ON
    freq-r14                        INTEGER (919750000..927250000)          OPTIONAL,   -- Need ON
    ...
}

-- ASN1STOP
-- ASN1START

TBS-RequestAssistanceData-r14 ::= SEQUENCE {
    mbs-AlmanacAssistanceDataReq-r14        BOOLEAN,
    mbs-AcquisitionAssistanceDataReq-r14    BOOLEAN,
    ...
}

-- ASN1STOP
-- ASN1START

Sensor-ProvideLocationInformation-r13 ::= SEQUENCE {
    sensor-MeasurementInformation-r13       Sensor-MeasurementInformation-r13       OPTIONAL,
    sensor-Error-r13                        Sensor-Error-r13                        OPTIONAL,
    ...
}

-- ASN1STOP
-- ASN1START

Sensor-MeasurementInformation-r13 ::= SEQUENCE {
    measurementReferenceTime-r13            UTCTime                     OPTIONAL,
    uncompensatedBarometricPressure-r13     INTEGER (30000..115000)     OPTIONAL, -- Cond Barometer
    ...,

    uncertainty-r14                 SEQUENCE {
                                    range-r14       INTEGER (0..1000),
                                    confidence-r14  INTEGER (1..100)
                                    }                                   OPTIONAL

}

-- ASN1STOP
-- ASN1START

Sensor-RequestLocationInformation-r13 ::= SEQUENCE {
    uncompensatedBarometricPressureReq-r13      BOOLEAN,
    ...,
      assistanceAvailability-r14              BOOLEAN     OPTIONAL    -- Need ON

}

-- ASN1STOP
-- ASN1START

Sensor-ProvideCapabilities-r13 ::= SEQUENCE {
    sensor-Modes-r13            BIT STRING {    standalone  (0),
                                                ue-assisted (1),
                                                ue-based    (2)} (SIZE (1..8)),
    ...,
      sensor-AssistanceDataSupportList-r14    Sensor-AssistanceDataSupportList-r14    OPTIONAL,
        periodicalReportingSupported-r14        PositioningModes                        OPTIONAL,
        idleStateForMeasurements-r14            ENUMERATED { required }                 OPTIONAL

}

Sensor-AssistanceDataSupportList-r14 ::= SEQUENCE {
    ...

}

-- ASN1STOP
-- ASN1START

Sensor-RequestCapabilities-r13 ::= SEQUENCE {
    ...
}

-- ASN1STOP
-- ASN1START

Sensor-Error-r13 ::= CHOICE {
    locationServerErrorCauses-r13       Sensor-LocationServerErrorCauses-r13,
    targetDeviceErrorCauses-r13         Sensor-TargetDeviceErrorCauses-r13,
    ...
}

-- ASN1STOP
-- ASN1START

Sensor-LocationServerErrorCauses-r13 ::= SEQUENCE {
    cause-r13       ENUMERATED  {   undefined,
                                    ...,
                                    assistanceDataNotSupportedByServer-v1420,
                                    assistanceDataSupportedButCurrentlyNotAvailableByServer-v1420
                                    },
    ...
}

-- ASN1STOP
-- ASN1START

Sensor-TargetDeviceErrorCauses-r13 ::= SEQUENCE {
    cause-r13           ENUMERATED      {   undefined,
                                            ...,
                                            assistanceDataMissing-v1420
                                        },
    ...
}

-- ASN1STOP
-- ASN1START

Sensor-ProvideAssistanceData-r14 ::= SEQUENCE {
    sensor-AssistanceDataList-r14       Sensor-AssistanceDataList-r14       OPTIONAL,   -- Need ON
    sensor-Error-r14                    Sensor-Error-r13                    OPTIONAL,   -- Need ON
    ...
}

-- ASN1STOP
-- ASN1START

Sensor-AssistanceDataList-r14::= SEQUENCE {
    refPressure-r14     INTEGER (-20000..10000),
    refPosition-r14     EllipsoidPointWithAltitudeAndUncertaintyEllipsoid   OPTIONAL,   -- Need ON
    refTemperature-r14  INTEGER (-64..63)                                   OPTIONAL,   -- Need ON
    ...
}

-- ASN1STOP
-- ASN1START

Sensor-RequestAssistanceData-r14 ::= SEQUENCE {
    ...
}

-- ASN1STOP
-- ASN1START

WLAN-ProvideLocationInformation-r13 ::= SEQUENCE {
    wlan-MeasurementInformation-r13     WLAN-MeasurementInformation-r13     OPTIONAL,
    wlan-Error-r13                      WLAN-Error-r13                      OPTIONAL,
    ...
}

-- ASN1STOP
-- ASN1START

WLAN-MeasurementInformation-r13 ::= SEQUENCE {
    measurementReferenceTime-r13        UTCTime                     OPTIONAL,
    wlan-MeasurementList-r13            WLAN-MeasurementList-r13    OPTIONAL,
    ...
}

WLAN-MeasurementList-r13 ::= SEQUENCE (SIZE(1..maxWLAN-AP-r13)) OF WLAN-MeasurementElement-r13

WLAN-MeasurementElement-r13 ::= SEQUENCE {
    wlan-AP-Identifier-r13      WLAN-AP-Identifier-r13,
    rssi-r13                    INTEGER (-127..128)                 OPTIONAL,
    rtt-r13                     WLAN-RTT-r13                        OPTIONAL,
    apChannelFrequency-r13      INTEGER (0..256)                    OPTIONAL,
    servingFlag-r13             BOOLEAN                             OPTIONAL,
    ...
}

WLAN-AP-Identifier-r13 ::= SEQUENCE {
    bssid-r13                   OCTET STRING (SIZE (6)),
    ssid-r13                    OCTET STRING (SIZE (1..32))         OPTIONAL,
    ...
}

WLAN-RTT-r13 ::= SEQUENCE {
    rttValue-r13     INTEGER (0..16777215),
    rttUnits-r13     ENUMERATED {   microseconds,
                                    hundredsofnanoseconds,
                                    tensofnanoseconds,
                                    nanoseconds,
                                    tenthsofnanoseconds,
                                    ... },
    rttAccuracy-r13  INTEGER (0..255)                               OPTIONAL,
    ...
}

maxWLAN-AP-r13          INTEGER ::= 64

-- ASN1STOP
-- ASN1START

WLAN-RequestLocationInformation-r13 ::= SEQUENCE {
    requestedMeasurements-r13   BIT STRING {
                                            rssi        (0),
                                            rtt         (1)} (SIZE(1..8)),
    ...,
      assistanceAvailability-r14  BOOLEAN         OPTIONAL    -- Need ON

}

-- ASN1STOP
-- ASN1START

WLAN-ProvideCapabilities-r13 ::= SEQUENCE {
    wlan-Modes-r13          BIT STRING  {   standalone      (0),
                                            ue-assisted     (1),
                                            ue-based        (2)}    (SIZE (1..8)),
    wlan-MeasSupported-r13  BIT STRING  {
                                            rssi-r13        (0),
                                            rtt-r13         (1)}    (SIZE(1..8)),
    ... ,
      wlan-AP-AD-Supported-r14
                            BIT STRING {    ap-identifier   (0),
                                            ap-location     (1)}    (SIZE (1..8))
                                                                                    OPTIONAL,
        periodicalReportingSupported-r14    PositioningModes                        OPTIONAL,
        idleStateForMeasurements-r14
                            ENUMERATED {    required    }                           OPTIONAL

}

-- ASN1STOP
-- ASN1START

WLAN-RequestCapabilities-r13 ::= SEQUENCE {
    ...
}

-- ASN1STOP
-- ASN1START

WLAN-Error-r13 ::= CHOICE {
    locationServerErrorCauses-r13       WLAN-LocationServerErrorCauses-r13,
    targetDeviceErrorCauses-r13         WLAN-TargetDeviceErrorCauses-r13,
    ...
}

-- ASN1STOP
-- ASN1START

WLAN-LocationServerErrorCauses-r13 ::= SEQUENCE {
    cause-r13                               ENUMERATED  {undefined,
                                                        ...,
                                                        requestedADNotAvailable-v1420,
                                                        notAllrequestedADAvailable-v1420
                                                        },
    ...,
      apLocationDataUnavailable-r14       NULL    OPTIONAL        -- Need ON

}

-- ASN1STOP
-- ASN1START

WLAN-TargetDeviceErrorCauses-r13 ::= SEQUENCE {
    cause-r13                               ENUMERATED {undefined,
                                                        requestedMeasurementsNotAvailable,
                                                        notAllrequestedMeasurementsPossible,
                                                        ...
                                                        },
    wlan-AP-RSSI-MeasurementNotPossible-r13             NULL        OPTIONAL,
    wlan-AP-RTT-MeasurementNotPossible-r13              NULL        OPTIONAL,
    ...
}

-- ASN1STOP
-- ASN1START

WLAN-ProvideAssistanceData-r14 ::= SEQUENCE {
    wlan-DataSet-r14    SEQUENCE (SIZE (1..maxWLAN-DataSets-r14)) OF WLAN-DataSet-r14
                                                                            OPTIONAL,   -- Need ON
    wlan-Error-r14      WLAN-Error-r13                                      OPTIONAL,   -- Need ON
    ...
}

maxWLAN-DataSets-r14        INTEGER ::= 8

-- ASN1STOP
-- ASN1START

WLAN-DataSet-r14 ::= SEQUENCE {
    wlan-AP-List-r14                SEQUENCE (SIZE (1..maxWLAN-AP-r14)) OF WLAN-AP-Data-r14,
    supportedChannels-11a-r14       SupportedChannels-11a-r14       OPTIONAL,   -- Need ON
    supportedChannels-11bg-r14      SupportedChannels-11bg-r14      OPTIONAL,   -- Need ON
    ...
}

SupportedChannels-11a-r14 ::= SEQUENCE {
    ch34-r14        BOOLEAN,
    ch36-r14        BOOLEAN,
    ch38-r14        BOOLEAN,
    ch40-r14        BOOLEAN,
    ch42-r14        BOOLEAN,
    ch44-r14        BOOLEAN,
    ch46-r14        BOOLEAN,
    ch48-r14        BOOLEAN,
    ch52-r14        BOOLEAN,
    ch56-r14        BOOLEAN,
    ch60-r14        BOOLEAN,
    ch64-r14        BOOLEAN,
    ch149-r14       BOOLEAN,
    ch153-r14       BOOLEAN,
    ch157-r14       BOOLEAN,
    ch161-r14       BOOLEAN
}

SupportedChannels-11bg-r14 ::= SEQUENCE {
    ch1-r14         BOOLEAN,
    ch2-r14         BOOLEAN,
    ch3-r14         BOOLEAN,
    ch4-r14         BOOLEAN,
    ch5-r14         BOOLEAN,
    ch6-r14         BOOLEAN,
    ch7-r14         BOOLEAN,
    ch8-r14         BOOLEAN,
    ch9-r14         BOOLEAN,
    ch10-r14        BOOLEAN,
    ch11-r14        BOOLEAN,
    ch12-r14        BOOLEAN,
    ch13-r14        BOOLEAN,
    ch14-r14        BOOLEAN
}

maxWLAN-AP-r14      INTEGER ::= 128


-- ASN1STOP
-- ASN1START

WLAN-AP-Data-r14 ::= SEQUENCE {
    wlan-AP-Identifier-r14              WLAN-AP-Identifier-r13,
    wlan-AP-Location-r14                WLAN-AP-Location-r14        OPTIONAL,   -- Need ON
    ...
}

WLAN-AP-Location-r14 ::= SEQUENCE {
    locationDataLCI-r14                 LocationDataLCI-r14,
    ...
}

LocationDataLCI-r14 ::= SEQUENCE {
    latitudeUncertainty-r14             BIT STRING (SIZE (6)),
    latitude-r14                        BIT STRING (SIZE (34)),
    longitudeUncertainty-r14            BIT STRING (SIZE (6)),
    longitude-r14                       BIT STRING (SIZE (34)),
    altitudeUncertainty-r14             BIT STRING (SIZE (6))       OPTIONAL,   -- Need ON
    altitude-r14                        BIT STRING (SIZE (30))      OPTIONAL,   -- Need ON
    datum-r14                           BIT STRING (SIZE (8)),
    ...
}

-- ASN1STOP
-- ASN1START

WLAN-RequestAssistanceData-r14 ::= SEQUENCE {
    requestedAD-r14         BIT STRING {    ap-identifier       (0),
                                            ap-location         (1)}    (SIZE (1..8)),
    visibleAPs-r14          SEQUENCE (SIZE (1..maxVisibleAPs-r14)) OF WLAN-AP-Identifier-r13    OPTIONAL,
    wlan-AP-StoredData-r14  SEQUENCE (SIZE (1..maxKnownAPs-r14)) OF WLAN-AP-Identifier-r13  OPTIONAL,
    ...
}

maxVisibleAPs-r14           INTEGER ::= 32
maxKnownAPs-r14             INTEGER ::= 2048

-- ASN1STOP
-- ASN1START

BT-ProvideLocationInformation-r13 ::= SEQUENCE {
    bt-MeasurementInformation-r13       BT-MeasurementInformation-r13   OPTIONAL,
    bt-Error-r13                        BT-Error-r13                    OPTIONAL,
    ...
}

-- ASN1STOP
-- ASN1START

BT-MeasurementInformation-r13 ::= SEQUENCE {
    measurementReferenceTime-r13        UTCTime                     OPTIONAL,
    bt-MeasurementList-r13              BT-MeasurementList-r13      OPTIONAL,
    ...
}

BT-MeasurementList-r13 ::= SEQUENCE (SIZE(1..maxBT-Beacon-r13)) OF BT-MeasurementElement-r13


BT-MeasurementElement-r13 ::= SEQUENCE {
    btAddr-r13                      BIT STRING (SIZE (48)),
    rssi-r13                        INTEGER (-128..127)             OPTIONAL,
    ...
}

maxBT-Beacon-r13                INTEGER ::= 32

-- ASN1STOP
-- ASN1START

BT-RequestLocationInformation-r13 ::= SEQUENCE {
    requestedMeasurements-r13   BIT STRING {
                                            rssi        (0)} (SIZE(1..8)),
    ...
}

-- ASN1STOP
-- ASN1START

BT-ProvideCapabilities-r13 ::= SEQUENCE {
    bt-Modes-r13            BIT STRING {    standalone      (0),
                                            ue-assisted     (1)}    (SIZE (1..8)),
    bt-MeasSupported-r13    BIT STRING {    rssi-r13        (0)}    (SIZE (1..8)),
    ...,

    idleStateForMeasurements-r14
                            ENUMERATED {    required    }                           OPTIONAL,
    periodicalReportingSupported-r14
                            PositioningModes                                        OPTIONAL

}

-- ASN1STOP
-- ASN1START

BT-RequestCapabilities-r13 ::= SEQUENCE {
    ...
}

-- ASN1STOP
-- ASN1START

BT-Error-r13 ::= CHOICE {
    locationServerErrorCauses-r13       BT-LocationServerErrorCauses-r13,
    targetDeviceErrorCauses-r13         BT-TargetDeviceErrorCauses-r13,
    ...
}

-- ASN1STOP
-- ASN1START

BT-LocationServerErrorCauses-r13 ::= SEQUENCE {
    cause-r13                               ENUMERATED  {undefined, ...},
    ...
}

-- ASN1STOP
-- ASN1START

BT-TargetDeviceErrorCauses-r13 ::= SEQUENCE {
    cause-r13                               ENUMERATED {undefined,
                                                        requestedMeasurementsNotAvailable,
                                                        notAllrequestedMeasurementsPossible,
                                                        ...
                                                        },
    bt-Beacon-rssiMeasurementNotPossible-r13    NULL        OPTIONAL,
    ...
}

-- ASN1STOP
-- ASN1START

END
