SUPL-TRIGGERED-STOP DEFINITIONS AUTOMATIC TAGS ::=
BEGIN
EXPORTS Ver2-SUPLTRIGGEREDSTOP;
IMPORTS
StatusCode
FROM ULP-Components;
Ver2-SUPLTRIGGEREDSTOP::= SEQUENCE{
 statusCode StatusCode OPTIONAL,
 ...}
END
