SUPL-AUTH-REQ DEFINITIONS AUTOMATIC TAGS ::=
BEGIN
EXPORTS SUPLAUTHREQ;
IMPORTS
Ver
FROM ULP-Components
SETCapabilities
FROM SUPL-START;
SUPLAUTHREQ ::= SEQUENCE {
 ver Ver OPTIONAL,
sETCapabilities SETCapabilities OPTIONAL,
 ...}
END
