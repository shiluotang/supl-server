SUPL-AUTH-RESP DEFINITIONS AUTOMATIC TAGS ::=
BEGIN
EXPORTS SUPLAUTHRESP;
IMPORTS
SPCSETKey, SPCTID, SPCSETKeylifetime
FROM Ver2-ULP-Components;
SUPLAUTHRESP ::= SEQUENCE {
 sPCSETKey SPCSETKey,
 spctid SPCTID,
 sPCSETKeylifetime SPCSETKeylifetime OPTIONAL,
 ...}
END
