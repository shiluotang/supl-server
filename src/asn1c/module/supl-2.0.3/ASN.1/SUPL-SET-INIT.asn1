SUPL-SET-INIT DEFINITIONS AUTOMATIC TAGS ::=
BEGIN
EXPORTS Ver2-SUPLSETINIT;
IMPORTS
SETId, QoP
FROM ULP-Components
ApplicationID
FROM Ver2-ULP-Components;
Ver2-SUPLSETINIT ::= SEQUENCE {
 targetSETID SETId, --Target SETid identifies the target SET to be located
 qoP QoP OPTIONAL,
 applicationID ApplicationID OPTIONAL,
 ...}
END
