SUPL-POS-INIT DEFINITIONS AUTOMATIC TAGS ::=
BEGIN
EXPORTS SUPLPOSINIT;
IMPORTS
SUPLPOS
FROM SUPL-POS
SETCapabilities
FROM SUPL-START
LocationId, Position, Ver
FROM ULP-Components
Ver2-SUPL-POS-INIT-extension
FROM ULP-Version-2-message-extensions
Ver2-RequestedAssistData-extension
FROM ULP-Version-2-parameter-extensions;
SUPLPOSINIT ::= SEQUENCE {
 sETCapabilities SETCapabilities,
 requestedAssistData RequestedAssistData OPTIONAL,
 locationId LocationId,
 position Position OPTIONAL,
 suplpos SUPLPOS OPTIONAL,
 ver Ver OPTIONAL,
 ...,
-- version 2 extension element
 ver2-SUPL-POS-INIT-extension Ver2-SUPL-POS-INIT-extension OPTIONAL}
RequestedAssistData ::= SEQUENCE {
 almanacRequested BOOLEAN,
 utcModelRequested BOOLEAN,
 ionosphericModelRequested BOOLEAN,
 dgpsCorrectionsRequested BOOLEAN,
 referenceLocationRequested BOOLEAN, -- Note: Used also for GANSS
 referenceTimeRequested BOOLEAN,
 acquisitionAssistanceRequested BOOLEAN,
realTimeIntegrityRequested BOOLEAN,
 navigationModelRequested BOOLEAN,
 navigationModelData NavigationModel OPTIONAL,
 ...,
 ver2-RequestedAssistData-extension Ver2-RequestedAssistData-extension
OPTIONAL}
NavigationModel ::= SEQUENCE {
 gpsWeek INTEGER(0..1023),
 gpsToe INTEGER(0..167),
 nsat INTEGER(0..31),
 toeLimit INTEGER(0..10),
 satInfo SatelliteInfo OPTIONAL,
...}
-- Further information on this fields can be found
-- in [3GPP RRLP]and [3GPP 49.031]
SatelliteInfo ::= SEQUENCE (SIZE (1..31)) OF SatelliteInfoElement
SatelliteInfoElement ::= SEQUENCE {
 satId INTEGER(0..63),
 iode INTEGER(0..255),
 ...}
END
